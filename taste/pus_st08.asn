-- H2020 ESROCOS Project
-- Company: GMV Aerospace & Defence S.A.U.
-- Licence: GPLv2

-- ASN.1 definitions for service ST[08] Function management
-- (cf. ECSS-E-ST-70-41C sections 6.8, 8.8)
--
-- The only one subservice is implemented:
--  - TC[8,1] Perform a function (no arguments for functions)



PUS-ST08 DEFINITIONS ::= 
BEGIN


    IMPORTS 
    PusUInt32, PusUInt64 FROM PUS-TypesDefinitions
    ;
    
    -- Event definition identifier
    PusSt08FunctionId ::= PusUInt32
        

    
    -- Data for TC[8,1], Perform a function request
    PusTC-8-1-Data  ::= SEQUENCE
    {
    	functionId PusSt08FunctionId
    }
    
END

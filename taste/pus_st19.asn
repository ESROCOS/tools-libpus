-- H2020 ESROCOS Project
-- Company: GMV Aerospace & Defence S.A.U.
-- Licence: GPLv2

-- ASN.1 definitions for service ST[19] Event-Action
-- (cf. ECSS-E-ST-70-41C sections 6.19, 8.19)
--
-- Limitations:
-- * Only the minimal services are implemented
--    TC-19-1 Add Event Action Definitions
--    TC-19-2 Delete Event Action Definitions
--    TC-19-4 Enable Event Action Definitions
--    TC-19-5 Disable Event Action Definitions



PUS-ST19 DEFINITIONS ::=
BEGIN

  IMPORTS 
  PusUInt32, PusUInt64 FROM PUS-TypesDefinitions
  PusSt05EventId FROM PUS-ST05
  ;
    
    
    -- Data for TC[19,X] (except for TC[19,1]), event action
  PusTC-19-X-Data ::= SEQUENCE
  {
 -- 	-- Just 1 action-event per TC
 -- 	-- No Aplication Process ID in TC packet
    	eventId PusSt05EventId
  }
    
END

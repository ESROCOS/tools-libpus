Context-pusservices DEFINITIONS ::=
BEGIN
   IMPORTS
      PusApid FROM PUS-CcsdsPacketFields;

--  Group all context parameters of this function in a record
Context-pusservices ::= SEQUENCE {
   apid PusApid

}

--  Declare a constant with the values set by the user in the interface view
pusservices-ctxt Context-pusservices ::= {
   apid 1

}
END

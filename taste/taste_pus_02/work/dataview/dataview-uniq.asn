-- H2020 ESROCOS Project
-- Company: GMV Aerospace & Defence S.A.U.
-- Licence: GPLv2

-- ASN.1 definitions for CCSDS packets
-- (cf. ECSS-E-ST-70-41C section 7.4)

PUS-CcsdsPacket DEFINITIONS ::=
BEGIN

	IMPORTS 
	PusTime FROM PUS-Time
	
	PusServiceType, PusSubserviceType FROM PUS-Services
	
	PusVersionNumber, PusTimeReferenceStatus, PusMessageTypeCounter, PusPacketType, PusApid, 
	PusChecksum, PusAcknowledgementFlags, PusPacketVersion, PusSecondaryHeaderFlag, PusSequenceFlags, 
	PusSequenceCount, PusPacketDataLength FROM PUS-CcsdsPacketFields

	PusTM-1-X-Data FROM PUS-ST01
	PusTM-3-25-Data FROM PUS-ST03
	PusTM-5-X-Data FROM PUS-ST05
	PusTC-8-1-Data FROM PUS-ST08
	PusTC-9-1-Data, PusTM-9-2-Data FROM PUS-ST09
	PusTC-12-1-2-Data  FROM PUS-ST12
	PusTC-19-X-Data FROM PUS-ST19
	PusTC-TM-20-X-Data FROM PUS-ST20
  	
	PusTC-18-1-Data, PusTC-18-2-6-12-Data, PusTC-18-3-Data, 
	PusTC-18-4-5-Data, PusTC-18-13-Data FROM PUS-ST18
	
	PusTC-TM-23-1-4-Data, PusTC-23-2-3-Data, PusTC-23-14-Data FROM PUS-ST23
  	
  	PusSt05EventId FROM PUS-ST05 -- for PusTC-19-X-Data
  	
  	PusUInt32 FROM PUS-TypesDefinitions
  	
  	pus-ST11-MAX-SCHEDULED-ACTIVITIES FROM PUS-Config

    PusTM-200-2-Data FROM PUS-ST200                     --  planner  
    PusTC-200-3-Data, PusTM-200-4-Data FROM PUS-ST200   --  mission  
    PusTC-200-5-Data, PusTM-200-6-Data FROM PUS-ST200   --  hotdockcmd  
    PusTM-200-8-Data FROM PUS-ST200                     --  hotdockstatus  
    PusTC-200-9-Data, PusTM-200-10-Data FROM PUS-ST200  --  wmcmd  
    PusTC-200-11-Data, PusTM-200-12-Data FROM PUS-ST200 --  basecmd  
    PusTC-200-13-Data, PusTM-200-14-Data FROM PUS-ST200 --  efcmd  
    
    PusTC-220-1-Data, PusTM-220-3-Data FROM PUS-ST220   --  reconfiguration
  	;

    -- dummy data field for packets with no data
    PusTM-TC-Dummy-Data ::= PusUInt32

    -- TM secondary header
    PusTmHeader ::= SEQUENCE
    {
        pusVersion      PusVersionNumber,
        timeRefStatus   PusTimeReferenceStatus,
        serviceId       PusServiceType,
        subtypeId       PusSubserviceType,
        msgTypeCount    PusMessageTypeCounter,
        destination     PusApid,
        time            PusTime
        -- no spare bits
    }
    
    -- TM actual data
    PusTmSourceData ::= CHOICE
    {
        st-0-0  PusTM-TC-Dummy-Data,
        st-1-X 	PusTM-1-X-Data,
        st-3-25 PusTM-3-25-Data,
        st-5-X 	PusTM-5-X-Data,
        st-9-2 	PusTM-9-2-Data,
        st-20-2 PusTC-TM-20-X-Data,
        st-23-4 PusTC-TM-23-1-4-Data,
        st-200-2 PusTM-200-2-Data, 
        st-200-4 PusTM-200-4-Data, 
        st-200-6 PusTM-200-6-Data, 
        st-200-8 PusTM-200-8-Data, 
        st-200-10 PusTM-200-10-Data, 
        st-200-12 PusTM-200-12-Data, 
        st-200-14 PusTM-200-14-Data,
        st-220-3 PusTM-220-3-Data
    }
    
    -- TC secondary header
    PusTcHeader ::= SEQUENCE
    {
        pusVersion      PusVersionNumber,
        ackFlags        PusAcknowledgementFlags,
        serviceId       PusServiceType,
        subtypeId       PusSubserviceType,
        source          PusApid
        -- no spare bits
    }
    
    
    -- Data for TM[19,1], event action
    PusTC-19-1-Data  ::= SEQUENCE
    {
    	-- Just 1 action-event per TC
    	-- No Aplication Process ID in TC packet
    	eventId 		PusSt05EventId,
    	packetReduced 	PusPacketReduced
    }
    
    -- Schedulable action TC11.4
    PusTcScheduledActivity ::= SEQUENCE
    {	
    	time			PusTime,
    	packetReduced 	PusPacketReduced
    }
    
    -- Data field for TC11.4
    PusTC-11-4-Data ::= SEQUENCE SIZE(1..pus-ST11-MAX-SCHEDULED-ACTIVITIES) OF PusTcScheduledActivity
           
    
    -- TC actual data
    PusTcApplicationData ::= CHOICE
    { -- The same order as the reduced
        st-0-0      PusTM-TC-Dummy-Data,
    	st-8-1 		PusTC-8-1-Data,
    	st-9-1 		PusTC-9-1-Data,
    	st-12-1-2 	PusTC-12-1-2-Data,
    	st-18-2-6-12 PusTC-18-2-6-12-Data,
    	st-18-3		PusTC-18-3-Data,
    	st-18-4-5	PusTC-18-4-5-Data,
    	st-18-13 	PusTC-18-13-Data,
    	st-19-X 	PusTC-19-X-Data,
    	st-20-X 	PusTC-TM-20-X-Data,
    	st-23-1		PusTC-TM-23-1-4-Data,
    	st-23-2-3	PusTC-23-2-3-Data,
    	st-23-14	PusTC-23-14-Data, 
        st-200-3 PusTC-200-3-Data, 
        st-200-5 PusTC-200-5-Data, 
        st-200-9 PusTC-200-9-Data, 
        st-200-11 PusTC-200-11-Data, 
        st-200-13 PusTC-200-13-Data,
        st-220-1 PusTC-220-1-Data,
    	-- No packet reduced
    	st-11-4 	PusTC-11-4-Data,
    	st-18-1 	PusTC-18-1-Data,
    	st-19-1 	PusTC-19-1-Data
    }
    
    PusTcApplicationDataReduced ::= CHOICE
    {
        st-0-0      PusTM-TC-Dummy-Data,
    	st-8-1 		PusTC-8-1-Data,
    	st-9-1 		PusTC-9-1-Data,
    	st-12-1-2 	PusTC-12-1-2-Data,
    	st-18-2-6-12 PusTC-18-2-6-12-Data,
    	st-18-3		PusTC-18-3-Data,
    	st-18-4-5	PusTC-18-4-5-Data,
    	st-18-13 	PusTC-18-13-Data,
    	st-19-X 	PusTC-19-X-Data,
    	st-20-X 	PusTC-TM-20-X-Data,
    	st-23-1		PusTC-TM-23-1-4-Data,
    	st-23-2-3	PusTC-23-2-3-Data,
    	st-23-14	PusTC-23-14-Data,
        st-200-3 PusTC-200-3-Data,
        st-200-5 PusTC-200-5-Data,
        st-200-9 PusTC-200-9-Data,
        st-200-11 PusTC-200-11-Data,
        st-200-13 PusTC-200-13-Data, 
        st-220-1 PusTC-220-1-Data
    }
    
    -- TM/TC header + data
    PusTmHeaderData ::= SEQUENCE
    {
       header  PusTmHeader,
        data    PusTmSourceData
    }
    PusTcHeaderDataTemplate{T} ::= SEQUENCE
    {
        header  PusTcHeader,
        data    T
    }
    
   -- PusTcHeaderData ::= PusTcHeaderDataTemplate{PusTcApplicationData}
   -- PusTcHeaderDataReduced ::= PusTcHeaderDataTemplate{PusTcApplicationDataReduced}


    -- Packet data
    PusPacketDataTemplate{T} ::= CHOICE
    {
        tmData          PusTmHeaderData,
        tmDataNoHeader  PusTmSourceData,
        tcData          PusTcHeaderDataTemplate{T},
        tcDataNoHeader  T
    }
    PusPacketData ::= PusPacketDataTemplate{PusTcApplicationData}
    PusPacketDataReduced ::= PusPacketDataTemplate{PusTcApplicationDataReduced}
    

    -- CCSDS packet
    -- TM/TC user data contains only the source/application data. No spare bits or checksum is used.
    -- Spare bits are not needed because TASTE handles the packing of the fields.
    -- Checksum is not used because TASTE handles encoding/decoding, and there might be 
    -- mismatched checksums if a message is transmitted between hosts with different endianness. 
    PusPacketTemplate{T} ::= SEQUENCE
    {
        packetVersion       PusPacketVersion,
        packetType          PusPacketType,
        secondaryHeaderFlag PusSecondaryHeaderFlag,
        apid                PusApid,
        sequenceFlags       PusSequenceFlags,
        sequenceCount       PusSequenceCount,
        dataLength          PusPacketDataLength,
        data                T
    }
    
    PusPacket ::= PusPacketTemplate {PusPacketData}
	PusPacketReduced ::= PusPacketTemplate {PusPacketDataReduced}


END

-- H2020 ESROCOS Project
-- Company: GMV Aerospace & Defence S.A.U.
-- Licence: GPLv2

-- ASN.1 definitions for CCSDS packets
-- (cf. ECSS-E-ST-70-41C section 7.4)

PUS-CcsdsPacketFields DEFINITIONS ::=
BEGIN

    IMPORTS 
    PusUInt4, PusUInt11, PusUInt14, PusUInt16, PusUInt32 FROM PUS-TypesDefinitions
    PusServiceType, PusSubserviceType FROM PUS-Services;


    -- Packet version number field
    PusPacketVersion ::= ENUMERATED
    {
        pus-CCSDS-V1  (0) -- Version 0 for CCSDS 133. 0-B-1 (version 1 CCSDS packet)
    }
    
    -- Default packet version
    pus-PACKET-VERSION-CURRENT PusPacketVersion ::= pus-CCSDS-V1

    -- Packet type field (1 bit)
    PusPacketType ::= ENUMERATED
    {
        pus-TM  (0),
        pus-TC  (1)
    }
    
    -- Packet secondary header flag (1 bit)
    PusSecondaryHeaderFlag ::= BOOLEAN
    
    -- Application Process ID (11 bits)
    PusApid ::= PusUInt11
    
    -- reserved APIDs
    pus-APID-TIME PusApid ::= 0       -- time packets
    pus-APID-IDLE PusApid ::= 2047    -- idle packets
    
    -- Sequence flags (3 bits)
    PusSequenceFlags ::= ENUMERATED
    {
        pus-STANDALONE-PACKET (3)     -- all PUS standard packets are standalone (11)
    }
    
    -- Sequence count (14 bits)
    PusSequenceCount ::= PusUInt14
    
    -- Packet data length (16 bits)
    PusPacketDataLength ::= PusUInt16

    -- PUS version numver (4 bits)
    PusVersionNumber ::= ENUMERATED
    {
        pus-V0               (0),   -- ESA PSS-07-101
        pus-V1               (1),   -- ECSS-E-70-41A
        pus-V2               (2),   -- ECSS-E-ST-70-41C
        pus-INVALID-VERSION (15)    -- Invalid value
    }
    
    pus-VERSION-CURRENT PusVersionNumber ::= pus-V2    -- current version
    
    -- Spacecraft time reference status
    PusTimeReferenceStatus ::= PusUInt4

    pus-TIME-REFERENCE-STATUS-NONE PusTimeReferenceStatus ::= 0 -- value for application processes without the capability to report it
    
    -- Message type counter (per destination and type)
    PusMessageTypeCounter ::= PusUInt16
    
    pus-MESSAGE-TYPE-COUNTER-NONE PusMessageTypeCounter ::= 0   -- value for application processes without such counter
    
    -- Acknowledgement flags (4 bits)
    PusAcknowledgementFlags ::= SEQUENCE
    {
        acceptanceReportRequested   BOOLEAN,
        startReportRequested        BOOLEAN,
        progressReportRequested     BOOLEAN,
        completionReportRequested   BOOLEAN
    }
    
    -- Packet error control checksum (16 bits)
    PusChecksum ::= PusUInt16
    
    -- Type to identify progress steps used e.g. by ST[01] and ST[18]
	PusStepId ::= PusUInt32
	
	pus-STEP-NONE PusStepId ::= 0	-- Null step value
    
END

-- H2020 ESROCOS Project
-- Company: GMV Aerospace & Defence S.A.U.
-- Licence: GPLv2

-- ASN.1 constant definitions related to the configuration of PUS services
--
-- This file centralizes some definitions regarding sizes, etc. of the PUS services.
-- 
-- Limitations:
-- These sizes could be derived from the mission configuration. However, in order to 
-- simplify code generation, they are currently defined here.


PUS-Config DEFINITIONS ::=
BEGIN

    IMPORTS 
    PusUInt32 FROM PUS-TypesDefinitions
    ;
    
    -- Dummy type, workaround for missing include bug in asn1.exe (TO-DO: remove when fixed)
    PusConfigDummyType ::= PusUInt32

    -- Maximum number of parameters in a housekeeping report
    pus-ST03-MAX-REPORT-LENGTH PusUInt32 ::= 20
    
    -- Maximun number of Scheduled Actions in a TC11.4 packet
    pus-ST11-MAX-SCHEDULED-ACTIVITIES PusUInt32 ::= 3
    
    -- Maximun number of character in OBCP ID (ST18)
    pus-ST18-SIZE-OBCP-ID PusUInt32 ::= 10
    
    -- Maximun number of character in OBCP Code TC[18,1] 
    pus-ST18-MAX-SIZE-OBCP-CODE PusUInt32 ::= 20000
    
    -- Maximun number of bits in OBCP CHECKSUM (ST18)
    pus-ST18-SIZE-OBCP-CHECKSUM PusUInt32 ::= 16
    
    -- Maximum number of character in file path (ST23)
    pus-ST23-MAX-SIZE-FILE-PATH PusUInt32 ::= 30
    
    -- Maximum number of character in repository path (ST23)
    pus-ST23-MAX-SIZE-REPOSITORY-PATH PusUInt32 ::= 30
    
    -- Maximum number of character in repository domain (ST23)
    pus-ST23-MAX-SIZE-REPOSITORY-DOMAIN PusUInt32 ::= 30
    
    -- Maximum size of a file in ST23
    pus-ST23-MAX-SIZE-FILE PusUInt32 ::= 1000

END

-- H2020 ESROCOS Project
-- Company: GMV Aerospace & Defence S.A.U.
-- Licence: GPLv2

-- ASN.1 definitions for the standard PUS services and subservices
-- (cf. ECSS-E-ST-70-41C)
-- Only a subset of the capabilities are implemented

PUS-Services DEFINITIONS ::=

BEGIN

	IMPORTS PusUInt8 FROM PUS-TypesDefinitions;

    -- PUS service types
    PusServiceType     ::= PusUInt8
    PusSubserviceType  ::= PusUInt8

    -- Default value
    pusService-NONE                         PusServiceType ::=  0

	-- Standard service types (1..127)
    pus-ST01-requestVerification            PusServiceType ::=  1
    pus-ST02-deviceAccess           	    PusServiceType ::=  2
    pus-ST03-housekeeping                   PusServiceType ::=  3
    pus-ST04-parameterStatisticsReporting   PusServiceType ::=  4
    pus-ST05-eventReporting                 PusServiceType ::=  5
    pus-ST06-memoryManagement               PusServiceType ::=  6
    -- reserved (7)
    pus-ST08-functionManagement             PusServiceType ::=  8
    pus-ST09-timeManagement                 PusServiceType ::=  9
    -- reserved (10)
    pus-ST11-timeBasedScheduling           PusServiceType ::= 11
    pus-ST12-onBoardMonitoring             PusServiceType ::= 12
    pus-ST13-largePacketTransfer           PusServiceType ::= 13
    pus-ST14-realTimeForwardingControl     PusServiceType ::= 14
    pus-ST15-onBoardStorageAndRetrieval    PusServiceType ::= 15
	-- reserved (16)
    pus-ST17-test                          PusServiceType ::= 17
    pus-ST18-onBoardControlProcedure       PusServiceType ::= 18
    pus-ST19-eventAction                   PusServiceType ::= 19
    pus-ST20-parameterManagement           PusServiceType ::= 20
    pus-ST21-requestSequencing             PusServiceType ::= 21
    pus-ST22-partitionBasedScheduling      PusServiceType ::= 22
    pus-ST23-fileManagement                PusServiceType ::= 23

	-- Standard service subtypes

    -- Default value
    pusSubtype-NONE                        PusSubserviceType ::=  0

	-- ST[01] Request Verification
	pus-TM-1-1-successfulAcceptance         PusSubserviceType ::=  1
	pus-TM-1-2-failedAcceptance             PusSubserviceType ::=  2
	pus-TM-1-3-successfulStart              PusSubserviceType ::=  3 
	pus-TM-1-4-failedStart                  PusSubserviceType ::=  4 
	pus-TM-1-5-successfulProgress           PusSubserviceType ::=  5 
	pus-TM-1-6-failedProgress               PusSubserviceType ::=  6 
	pus-TM-1-7-successfulCompletion         PusSubserviceType ::=  7 
	pus-TM-1-8-failedCompletion             PusSubserviceType ::=  8 
	-- pus-TM-1-10-failedRouting               PusSubserviceType ::= 10 -- NOT IMPLEMENTED
	
	-- ST[02] Device Access
	-- NOT IMPLEMENTED --
	
	-- ST[03] Housekeeping
	-- Housekeeping
	-- pus-TC-3-1-createHousekeepingStructure       PusSubserviceType ::=  1 -- NOT IMPLEMENTED
	-- pus-TC-3-3-deleteHousekeepingStructure       PusSubserviceType ::=  3 -- NOT IMPLEMENTED
	-- pus-TC-3-5-enablePeriodicHousekeeping        PusSubserviceType ::=  5 -- NOT IMPLEMENTED
	-- pus-TC-3-6-disablePeridodicHousekeeping      PusSubserviceType ::=  6 -- NOT IMPLEMENTED
	-- pus-TC-3-9-reportHousekeepingStructures      PusSubserviceType ::=  9 -- NOT IMPLEMENTED
	-- pus-TM-3-10-reportHousekeepingStructures     PusSubserviceType ::= 10 -- NOT IMPLEMENTED
	pus-TM-3-25-housekeepingReport               PusSubserviceType ::= 25
	-- pus-TC-3-27-oneShotHousekeeping              PusSubserviceType ::= 27 -- NOT IMPLEMENTED
	-- pus-TC-3-29-appendHousekeepingParameter      PusSubserviceType ::= 29 -- NOT IMPLEMENTED
	-- pus-TC-3-31-modifyHousekeepingInterval       PusSubserviceType ::= 31 -- NOT IMPLEMENTED
	-- pus-TC-3-33-reportHousekeepingPeriod         PusSubserviceType ::= 33 -- NOT IMPLEMENTED
	-- pus-TM-3-35-reportHousekeepingPeriod         PusSubserviceType ::= 35 -- NOT IMPLEMENTED

	-- Diagnostic
	-- pus-TC-3-2-createDiagnosticStructure         PusSubserviceType ::=   2 -- NOT IMPLEMENTED (LOW PRIORITY)
	-- pus-TC-3-4-deleteDiagnosticStructure         PusSubserviceType ::=   4 -- NOT IMPLEMENTED (LOW PRIORITY)
	-- pus-TC-3-7-enablePeriodicDiagnostic          PusSubserviceType ::=   7 -- NOT IMPLEMENTED (LOW PRIORITY)
	-- pus-TC-3-8-disablePeriodicDiagnostic         PusSubserviceType ::=   8 -- NOT IMPLEMENTED (LOW PRIORITY)
	-- pus-TC-3-11-reportDiagnosticStructures       PusSubserviceType ::=  11 -- NOT IMPLEMENTED
	-- pus-TM-3-12-reportDiagnosticStructures       PusSubserviceType ::=  12 -- NOT IMPLEMENTED
	-- pus-TM-3-26-diagnosticReport                 PusSubserviceType ::=  26 -- NOT IMPLEMENTED (LOW PRIORITY)
	-- pus-TC-3-28-oneShotDiagnostic                PusSubserviceType ::=  28 -- NOT IMPLEMENTED
	-- pus-TC-3-30-appendDiagnosticParameter        PusSubserviceType ::=  30 -- NOT IMPLEMENTED
	-- pus-TC-3-32-modifyDiagnosticInterval         PusSubserviceType ::=  32 -- NOT IMPLEMENTED
	-- pus-TC-3-34-reportDiagnosticPeriod           PusSubserviceType ::=  34 -- NOT IMPLEMENTED
	-- pus-TM-3-36-reportDiagnosticPeriod           PusSubserviceType ::=  36 -- NOT IMPLEMENTED

	-- Parameter functional reporting
	-- pus-TC-3-37-applyParameterFunctionalConfiguration    PusSubserviceType ::= 37 -- NOT IMPLEMENTED
	-- pus-TC-3-38-createParameterFunctionalDefinition      PusSubserviceType ::= 38 -- NOT IMPLEMENTED
	-- pus-TC-3-39-deleteParameterFunctionalDefinition      PusSubserviceType ::= 39 -- NOT IMPLEMENTED
	-- pus-TC-3-40-reportParameterFunctionalDefinitions     PusSubserviceType ::= 40 -- NOT IMPLEMENTED
	-- pus-TM-3-41-reportParameterFunctionalDefinitions     PusSubserviceType ::= 41 -- NOT IMPLEMENTED
	-- pus-TC-3-42-addParamterReportDefinition              PusSubserviceType ::= 42 -- NOT IMPLEMENTED
	-- pus-TC-3-43-removeParamterReportDefinition           PusSubserviceType ::= 43 -- NOT IMPLEMENTED
	-- pus-TC-3-44-modifyParameterFunctionalPeriod          PusSubserviceType ::= 44 -- NOT IMPLEMENTED

	-- ST[04] Parameter statistics reporting
	-- NOT IMPLEMENTED --

	-- ST[05] Event reporting
	pus-TM-5-1-eventInformative            PusSubserviceType ::= 1
	pus-TM-5-2-anomalyLowSeverity          PusSubserviceType ::= 2
	pus-TM-5-3-anomalyMediumSeverity       PusSubserviceType ::= 3
	pus-TM-5-4-anomalyHighSeverity         PusSubserviceType ::= 4
	-- pus-TC-5-5-enableEventReport           PusSubserviceType ::= 5 -- NOT IMPLEMENTED
	-- pus-TC-5-6-disableEventReport          PusSubserviceType ::= 6 -- NOT IMPLEMENTED
	-- pus-TC-5-7-reportDisabledEvents        PusSubserviceType ::= 7 -- NOT IMPLEMENTED
	-- pus-TM-5-8-reportDisabledEvents        PusSubserviceType ::= 8 -- NOT IMPLEMENTED
	
    -- ST[06] Memory management
    -- NOT IMPLEMENTED --

    -- ST[08] Function management
    pus-TC-8-1-performFunction		PusSubserviceType ::= 1
    
    -- ST[09] Time management
    pus-TC-9-1-setTimeReportRate     PusSubserviceType ::= 1
    pus-TM-9-2-cucTimeReport         PusSubserviceType ::= 2
    -- pus-TM-9-3-cdsTimeReport         PusSubserviceType ::= 3 -- NOT IMPLEMENTED (exclusive with TM[9,2])

	-- ST[11] Time-based scheduling
	pus-TC-11-1-enableTimeBasedScheduling        PusSubserviceType ::=  1
	pus-TC-11-2-disableTimeBasedScheduling       PusSubserviceType ::=  2
	pus-TC-11-3-resetTimeBasedSchedule           PusSubserviceType ::=  3
	pus-TC-11-4-insertActivity                   PusSubserviceType ::=  4
	-- pus-TC-11-5-deleteActivities                 PusSubserviceType ::=  5 -- NOT IMPLEMENTED
	-- pus-TC-11-6-deleteByFilter                   PusSubserviceType ::=  6 -- NOT IMPLEMENTED
	-- pus-TC-11-8-timeShiftByFilter                PusSubserviceType ::=  8 -- NOT IMPLEMENTED
	-- pus-TC-11-9-detailReportActivities           PusSubserviceType ::=  9 -- NOT IMPLEMENTED
	-- pus-TM-11-10-detailReport                    PusSubserviceType ::=  10 -- NOT IMPLEMENTED
	-- pus-TC-11-11-detailReportByFilter            PusSubserviceType ::=  11 -- NOT IMPLEMENTED
	-- pus-TC-11-12-summaryReportActivities         PusSubserviceType ::=  12 -- NOT IMPLEMENTED
	-- pus-TM-11-13-summaryReport                   PusSubserviceType ::=  13 -- NOT IMPLEMENTED
	-- pus-TC-11-14-summaryReportByFilter           PusSubserviceType ::=  14 -- NOT IMPLEMENTED
	-- pus-TC-11-15-timeShiftAllActivities          PusSubserviceType ::=  15 -- NOT IMPLEMENTED
	-- pus-TC-11-16-detailReportAll                 PusSubserviceType ::=  16 -- NOT IMPLEMENTED
	-- pus-TC-11-17-timeShiftActivities             PusSubserviceType ::=  17 -- NOT IMPLEMENTED
	-- pus-TC-11-18-reportSubschedulesStatus        PusSubserviceType ::=  18 -- NOT IMPLEMENTED
	-- pus-TM-11-19-reportSubschedulesStatus        PusSubserviceType ::=  19 -- NOT IMPLEMENTED
	-- pus-TC-11-20-enableSubschedules              PusSubserviceType ::=  20 -- NOT IMPLEMENTED
	-- pus-TC-11-21-disableSubschedules             PusSubserviceType ::=  21 -- NOT IMPLEMENTED
	-- pus-TC-11-22-createGroups                    PusSubserviceType ::=  22 -- NOT IMPLEMENTED
	-- pus-TC-11-23-deleteGroups                    PusSubserviceType ::=  23 -- NOT IMPLEMENTED
	-- pus-TC-11-24-enableGroups                    PusSubserviceType ::=  24 -- NOT IMPLEMENTED
	-- pus-TC-11-25-disableGroups                   PusSubserviceType ::=  25 -- NOT IMPLEMENTED
	-- pus-TC-11-26-reportGroupsStatus              PusSubserviceType ::=  26 -- NOT IMPLEMENTED
	-- pus-TM-11-27-reportGroupsStatus              PusSubserviceType ::=  27 -- NOT IMPLEMENTED
	
	-- ST[12] On-board monitoring
	-- Parameter monitoring
	pus-TC-12-1-enableParameterMonitoringDefinitions         PusSubserviceType ::=  1
	pus-TC-12-2-disableParameterMonitoringDefinitions        PusSubserviceType ::=  2
	-- pus-TC-12-3-changeReportingDelay                         PusSubserviceType ::=  3 -- NOT IMPLEMENTED
	-- pus-TC-12-4-deleteAllParameterMonitoringDefinitions      PusSubserviceType ::=  4 -- NOT IMPLEMENTED
	-- pus-TC-12-5-addParameterMonitoringDefinitions            PusSubserviceType ::=  5 -- NOT IMPLEMENTED
	-- pus-TC-12-6-deleteParameterMonitoringDefinitions         PusSubserviceType ::=  6 -- NOT IMPLEMENTED
	-- pus-TC-12-7-modifyParameterMonitoringDefinitions         PusSubserviceType ::=  7 -- NOT IMPLEMENTED
	-- pus-TC-12-8-reportParameterMonitoringDefinitions         PusSubserviceType ::=  8 -- NOT IMPLEMENTED
	-- pus-TM-12-9-reportParameterMonitoringDefinitions         PusSubserviceType ::=  9 -- NOT IMPLEMENTED
	-- pus-TC-12-10-reportOutOfLimits                           PusSubserviceType ::= 10 -- NOT IMPLEMENTED
	-- pus-TM-12-11-reportOutOfLimits                           PusSubserviceType ::= 11 -- NOT IMPLEMENTED
	-- pus-TM-12-12-checkTransitionReport                       PusSubserviceType ::= 12 -- NOT IMPLEMENTED (LOW PRIORITY)
	-- pus-TC-12-13-reportParameterMonitoringDefinitionsStatus  PusSubserviceType ::= 13 -- NOT IMPLEMENTED
	-- pus-TM-12-14-reportParameterMonitoringDefinitionsStatus  PusSubserviceType ::= 14 -- NOT IMPLEMENTED
	pus-TC-12-15-enableParameterMonitoring                   PusSubserviceType ::= 15
	pus-TC-12-16-disableParameterMonitoring                  PusSubserviceType ::= 16
	
	-- Functional monitoring
	-- pus-TC-12-17-enableFunctionalMonitoring                         PusSubserviceType ::= 17 -- NOT IMPLEMENTED
	-- pus-TC-12-18-disableFunctionalMonitoring                        PusSubserviceType ::= 18 -- NOT IMPLEMENTED
	-- pus-TC-12-19-enableFunctionalMonitoringDefinitions              PusSubserviceType ::= 19 -- NOT IMPLEMENTED
	-- pus-TC-12-20-disableFunctionalMonitoringDefinitions             PusSubserviceType ::= 20 -- NOT IMPLEMENTED
	-- pus-TC-12-21-protectFunctionalMonitoringDefinitions             PusSubserviceType ::= 21 -- NOT IMPLEMENTED
	-- pus-TC-12-22-unprotectFunctionalMonitoringDefinitions           PusSubserviceType ::= 22 -- NOT IMPLEMENTED
	-- pus-TC-12-23-addFunctionalMonitoringDefinitions                 PusSubserviceType ::= 23 -- NOT IMPLEMENTED
	-- pus-TC-12-24-deleteFunctionalMonitoringDefinitions              PusSubserviceType ::= 24 -- NOT IMPLEMENTED
	-- pus-TC-12-25-reportFunctionalMonitoringDefinitions              PusSubserviceType ::= 25 -- NOT IMPLEMENTED
	-- pus-TM-12-26-reportFunctionalMonitoringDefinitions              PusSubserviceType ::= 26 -- NOT IMPLEMENTED
	-- pus-TC-12-27-reportFunctionalMonitoringDefinitionsStatus        PusSubserviceType ::= 27 -- NOT IMPLEMENTED
	-- pus-TM-12-28-reportFunctionalMonitoringDefinitionsStatus        PusSubserviceType ::= 28 -- NOT IMPLEMENTED
	
	-- ST[13] Large packet transfer
	-- NOT IMPLEMENTED --
	
	-- ST[14] Real-time forwarding control
	-- NOT IMPLEMENTED --
	
	-- ST[15] On-board storage and retrieval
	-- NOT IMPLEMENTED --
	
	-- ST[17] Test
	pus-TC-17-1-connectionTest           PusSubserviceType ::= 1
	pus-TM-17-2-connectionTest           PusSubserviceType ::= 2
	-- pus-TC-17-3-onboardConnectionTest    PusSubserviceType ::= 3 -- NOT IMPLEMENTED
	-- pus-TM-17-4-onboardConnectionTest    PusSubserviceType ::= 4 -- NOT IMPLEMENTED

	-- ST[18] On-board operations procedure
	-- OBCP management
	pus-TC-18-1-loadObcpDirect                   PusSubserviceType ::= 1
	pus-TC-18-2-unloadObcp                       PusSubserviceType ::= 2
	pus-TC-18-3-activateObcp                     PusSubserviceType ::= 3
	pus-TC-18-4-stopObcp                         PusSubserviceType ::= 4
	pus-TC-18-5-suspendObcp                      PusSubserviceType ::= 5
	pus-TC-18-6-resumeObcp                       PusSubserviceType ::= 6
	-- pus-TC-18-7-communicateParameters            PusSubserviceType ::= 7 -- NOT IMPLEMENTED
	-- pus-TC-18-8-reportExecutionStatus            PusSubserviceType ::= 8 -- NOT IMPLEMENTED
	-- pus-TM-18-9-reportExecutionStatus            PusSubserviceType ::= 9 -- NOT IMPLEMENTED
	pus-TC-18-12-abortObcp                       PusSubserviceType ::= 12
	pus-TC-18-13-loadObcpByReference             PusSubserviceType ::= 13
	-- pus-TC-18-14-activateAndExecuteStep          PusSubserviceType ::= 14 -- NOT IMPLEMENTED
	-- pus-TC-18-15-resumeAndExecuteStep            PusSubserviceType ::= 15 -- NOT IMPLEMENTED
	-- pus-TC-18-16-setObservabilityLevel           PusSubserviceType ::= 16 -- NOT IMPLEMENTED
	-- pus-TC-18-17-abortAllObcpsAndReport          PusSubserviceType ::= 17 -- NOT IMPLEMENTED
	-- pus-TC-18-18-abortedObcpReport               PusSubserviceType ::= 18 -- NOT IMPLEMENTED
	-- pus-TC-18-19-loadByReferenceAndActivateObcp  PusSubserviceType ::= 19 -- NOT IMPLEMENTED
	-- pus-TC-18-20-stopAndUnloadObcp               PusSubserviceType ::= 20 -- NOT IMPLEMENTED
	
	-- OBCP engine management
	pus-TC-18-21-startObcpEngine                 PusSubserviceType ::= 21
	pus-TC-18-22-stopObcpEngine                  PusSubserviceType ::= 22

    -- ST[19] Event-action
    pus-TC-19-1-addEventActionDefinitions        PusSubserviceType ::=  1
    pus-TC-19-2-deleteEventActionDefinitions     PusSubserviceType ::=  2 
    -- pus-TC-19-3-deleteAllEventActionDefinitions  PusSubserviceType ::=  3 -- NOT IMPLEMENTED
    pus-TC-19-4-enableEventActionDefinitions     PusSubserviceType ::=  4
    pus-TC-19-5-disableEventActionDefinitions    PusSubserviceType ::=  5
    -- pus-TC-19-6-reportAllEventActionDefinitions  PusSubserviceType ::=  6 -- NOT IMPLEMENTED
    -- pus-TM-19-7-reportEventActionDefinitions     PusSubserviceType ::=  7 -- NOT IMPLEMENTED
    -- pus-TC-19-8-enableEventActionFunction        PusSubserviceType ::=  8 -- NOT IMPLEMENTED
    -- pus-TC-19-9-disableEventActionFunction       PusSubserviceType ::=  9 -- NOT IMPLEMENTED
    -- pus-TC-19-10-reportEventActionDefinitions    PusSubserviceType ::= 10 -- NOT IMPLEMENTED

    -- ST[20] Parameter management
    pus-TC-20-1-reportParameterValues            PusSubserviceType ::= 1
    pus-TM-20-2-reportParameterValues            PusSubserviceType ::= 2
    pus-TC-20-3-setParameterValues               PusSubserviceType ::= 3
    -- pus-TC-20-4-changeRawMemoryDefinitions       PusSubserviceType ::= 4 -- NOT IMPLEMENTED
    -- pus-TC-20-5-changeObjectMemoryDefinitions    PusSubserviceType ::= 5 -- NOT IMPLEMENTED
    -- pus-TC-20-6-reportParameterDefinitions       PusSubserviceType ::= 6 -- NOT IMPLEMENTED
    -- pus-TM-20-7-reportParameterDefinitions       PusSubserviceType ::= 7 -- NOT IMPLEMENTED

    -- ST[21] Request sequencing
	-- NOT IMPLEMENTED --

    -- ST[22] Position-based scheduling
	-- NOT IMPLEMENTED --

    -- ST[23] File management
    -- File handling
    pus-TC-23-1-createFile                       PusSubserviceType ::=  1
    pus-TC-23-2-deleteFile                       PusSubserviceType ::=  2
    pus-TC-23-3-reportFileAttributes             PusSubserviceType ::=  3
    pus-TM-23-4-reportFileAttributes             PusSubserviceType ::=  4
    -- pus-TC-23-5-lockFile                         PusSubserviceType ::=  5
    -- pus-TC-23-6-unlockFile                       PusSubserviceType ::=  6
    -- pus-TC-23-7-findFiles                        PusSubserviceType ::=  7
    -- pus-TM-23-8-findFiles                        PusSubserviceType ::=  8
    -- pus-TC-23-9-createDirectory                  PusSubserviceType ::=  9
    -- pus-TC-23-10-deleteDirectory                 PusSubserviceType ::= 10
    -- pus-TC-23-11-renameDirectory                 PusSubserviceType ::= 11
    -- pus-TC-23-12-summaryReport                   PusSubserviceType ::= 12
    -- pus-TM-23-13-summaryReport                   PusSubserviceType ::= 13
    
    -- File copy
    pus-TC-23-14-copyFile                        PusSubserviceType ::= 14
    -- pus-TC-23-15-moveFile                        PusSubserviceType ::= 15
    -- pus-TC-23-16-suspendFileCopyOperations       PusSubserviceType ::= 16
    -- pus-TC-23-17-resumeFileCopyOperations        PusSubserviceType ::= 17
    -- pus-TC-23-18-abortFileCopyOperations         PusSubserviceType ::= 18
    -- pus-TC-23-19-suspendFileCopiesOfRepository   PusSubserviceType ::= 19
    -- pus-TC-23-20-resumeFileCopiesOfRepository    PusSubserviceType ::= 20
    -- pus-TC-23-21-abortFileCopiesOfRepository     PusSubserviceType ::= 21
    -- pus-TC-23-22-enablePerodicCopyReporting      PusSubserviceType ::= 22
    -- pus-TM-23-23-fileCopyStatusReport            PusSubserviceType ::= 23
    -- pus-TC-23-24-disablePerodicCopyReporting     PusSubserviceType ::= 24


	-- private services
	-- ST200 Agent
	pus-ST200-timelineControl 		PusServiceType ::= 200 
    pus-TM-200-2-plannerReport			PusSubserviceType ::= 2
     
    pus-TC-200-3-missionRequest			PusSubserviceType ::= 3 
    pus-TM-200-4-missionReport			PusSubserviceType ::= 4
     
    pus-TC-200-5-hotdockcmdRequest		PusSubserviceType ::= 5 
    pus-TM-200-6-hotdockcmdReport		PusSubserviceType ::= 6
     
    pus-TM-200-8-hotdockstatusReport	PusSubserviceType ::= 8
     
    pus-TC-200-9-wmcmdRequest			PusSubserviceType ::= 9 
    pus-TM-200-10-wmcmdReport			PusSubserviceType ::= 10
     
    pus-TC-200-11-basecmdRequest		PusSubserviceType ::= 11 
    pus-TM-200-12-basecmdReport			PusSubserviceType ::= 12
     
    pus-TC-200-13-efcmdRequest			PusSubserviceType ::= 13 
    pus-TM-200-14-efcmdReport			PusSubserviceType ::= 14
    
	-- ST220 SW-reconfiguration
    pus-ST220-reconfigurationControl 	PusServiceType ::= 220 
	pus-TC-220-1-setTargetState				PusSubserviceType ::= 1
    pus-TC-220-2-getCurrentState			PusSubserviceType ::= 2 
    pus-TM-220-3-reportCurrentState			PusSubserviceType ::= 3
    

END

-- H2020 ESROCOS Project
-- Company: GMV Aerospace & Defence S.A.U.
-- Licence: GPLv2

-- ASN.1 definitions for service ST[01] telecommand verification
-- (cf. ECSS-E-ST-70-41C sections 6.1.4.3, 8.1)
--
-- This file defines some error codes for TC verification. Additional error codes 
-- can be added 


PUS-ST01 DEFINITIONS ::=
BEGIN

    IMPORTS 
    PusPacketVersion, PusPacketType, PusSecondaryHeaderFlag, PusApid, PusSequenceFlags, PusSequenceCount, PusStepId FROM PUS-CcsdsPacketFields
    PusInt32, PusUInt32, PusUInt64, PusMemAddr FROM PUS-TypesDefinitions;
    
    -- Type to represent failure codes used by service ST[01]
    PusSt01FailureCode ::= PusUInt32
    
    -- Default failure codes (others may be added)
    pus-ST01-NO-ERROR					PusSt01FailureCode ::= 0	-- Default value
    pus-ST01-ERROR-APID-UNAVAILABLE		PusSt01FailureCode ::= 1	-- Destination process not available
    pus-ST01-ERROR-SERVICE-UNAVAILABLE	PusSt01FailureCode ::= 2	-- PUS service not available
    pus-ST01-ERROR-SUBTYPE-UNAVAILABLE	PusSt01FailureCode ::= 3	-- PUS service subtype not available	
    pus-ST01-ERROR-APID-UNKNOWN			PusSt01FailureCode ::= 4	-- Destination process is unknown
    pus-ST01-ERROR-SERVICE-UNKNOWN		PusSt01FailureCode ::= 5	-- PUS service is unknown
    pus-ST01-ERROR-SUBTYPE-UNKNOWN		PusSt01FailureCode ::= 6	-- PUS service subtype is unknown	
    pus-ST01-ERROR-WRONG-FORMAT			PusSt01FailureCode ::= 7	-- Packet format is inconsistent
    pus-ST01-ERROR-CHECKSUM				PusSt01FailureCode ::= 8	-- Checksums are currently not used, code reserved for future use
    
	-- Type to report failure data in ST[01] TM messages
	-- The type matches the error information stored by the PUS library (pus_error.h). Fields will be
	-- used optionally, depending on the code.
	PusSt01FailureInfo ::= SEQUENCE
	{
		subcode	PusInt32,	-- Internal error code, matching a C enum
		data	PusInt32,	-- Error data
		address PusMemAddr	-- A memory address
	}

    -- Request ID, used by ST[01] packets
    PusSt01RequestId ::= SEQUENCE
    {
        packetVersion       PusPacketVersion,
        packetType          PusPacketType,
        secondaryHeaderFlag PusSecondaryHeaderFlag,
        apid                PusApid,
        sequenceFlags       PusSequenceFlags,
        sequenceCount       PusSequenceCount
    }
    
    -- Failure notice, used by ST[01] packets
    PusSt01Failure ::= SEQUENCE
    {
    	code	PusSt01FailureCode,
    	info	PusSt01FailureInfo
    }
    
    -- Data of ST[01] TM packets
    -- Each packet type uses a subset of the fields, but it has been preferred to keep 
    -- the same structure for all to reduce the amount of code  
    PusTM-1-X-Data ::= SEQUENCE
    {
    	request	PusSt01RequestId,
    	step	PusStepId,
    	failure	PusSt01Failure
    }
    
    
END

-- H2020 ESROCOS Project
-- Company: GMV Aerospace & Defence S.A.U.
-- Licence: GPLv2

-- ASN.1 definitions for service ST[03] Housekeeping
-- (cf. ECSS-E-ST-70-41C sections 6.3.3, 8.3)
--
-- In order to allow for the implementation of the service using TASTE or a plain C application, 
-- the periodic generation of housekeeping or diagnostic reports is not managed; the library 
-- provides a call to generate a housekeeping TM, which should be invoked periodically by 
-- a periodic task external to the library
--
-- Limitations:
-- * Among the minimal services, diagnostic reports are not implemented (low priority)
-- * All housekeeping parameters are reported in an array of 64 bit elements, regardless of their 
--   actual length
-- * The size of the housekeeping report is defined by a constant not derived from the mission
--   database


PUS-ST03 DEFINITIONS ::=
BEGIN

    IMPORTS 
    PusUInt32, PusUInt64 FROM PUS-TypesDefinitions
    PusConfigDummyType, pus-ST03-MAX-REPORT-LENGTH FROM PUS-Config
    ;
    
    -- StoredParam of reports
    PusSt03StoredParam ::= PusUInt64
    
    -- Identifier of housekeeping reports
    PusSt03HousekeepingReportId ::= PusUInt32
    
    -- Default report, if only TM[3,25] implemented
    pus-ST03-DEFAULT-HK-REPORT PusSt03HousekeepingReportId ::= 0 
    
    -- Identifier of housekeeping/diagnostic parameters
    PusSt03ParameterId ::= PusUInt32
    
    -- Array of parameters in the report (all stored as PusUInt64)
    PusSt03ParameterArray ::= SEQUENCE (SIZE(0 .. pus-ST03-MAX-REPORT-LENGTH)) OF PusSt03StoredParam
    
    -- Data for TM[3,25], housekeeping parameter report
    PusTM-3-25-Data ::= SEQUENCE
    {
    	reportId PusSt03HousekeepingReportId,
    	parameters PusSt03ParameterArray
    }
    
    
END

-- H2020 ESROCOS Project
-- Company: GMV Aerospace & Defence S.A.U.
-- Licence: GPLv2

-- ASN.1 definitions for service ST[05] Event reporting
-- (cf. ECSS-E-ST-70-41C sections 6.5, 8.5)
--
-- Limitations:
-- * Only the minimal services (event reports are implemented); enabling/disabling events is not included
-- * All events use the same structure for their auxiliary data


PUS-ST05 DEFINITIONS ::=
BEGIN

    IMPORTS 
    PusUInt32, PusUInt64 FROM PUS-TypesDefinitions
    ;
    
    -- Event definition identifier
    PusSt05EventId ::= PusUInt32
    
    -- EventId none
    pus-EVENT-ID-NONE PusSt05EventId ::= 0

	-- Event auxiliary data
	PusSt05EventAuxData ::= SEQUENCE
	{
		data1 PusUInt64,
		data2 PusUInt64
	}
	
	-- AuxData none
	pus-EVENT-AUXDATA-NONE PusSt05EventAuxData ::= 
	{
		data1 0, 
		data2 0
	}
	
	-- Event dataStored none
	pus-EVENT-DATASTORED-NONE PusUInt64 ::= 0
	
	-- Event and data
	PusSt05Event ::= SEQUENCE
   {
    	eventId PusSt05EventId,
    	data PusSt05EventAuxData
   }
    
    -- Data for TM[5,1] to TM[5,4] event/anomaly reports
    PusTM-5-X-Data ::= PusSt05Event    
    
END

-- H2020 ESROCOS Project
-- Company: GMV Aerospace & Defence S.A.U.
-- Licence: GPLv2

-- ASN.1 definitions for service ST[08] Function management
-- (cf. ECSS-E-ST-70-41C sections 6.8, 8.8)
--
-- The only one subservice is implemented:
--  - TC[8,1] Perform a function (no arguments for functions)



PUS-ST08 DEFINITIONS ::= 
BEGIN


    IMPORTS 
    PusUInt32, PusUInt64 FROM PUS-TypesDefinitions
    ;
    
    -- Event definition identifier
    PusSt08FunctionId ::= PusUInt32
        

    
    -- Data for TC[8,1], Perform a function request
    PusTC-8-1-Data  ::= SEQUENCE
    {
    	functionId PusSt08FunctionId
    }
    
END

-- H2020 ESROCOS Project
-- Company: GMV Aerospace & Defence S.A.U.
-- Licence: GPLv2

-- ASN.1 definitions for service ST[09] Time management
-- (cf. ECSS-E-ST-70-41C sections 6.9, 8.9)
--
-- Limitations:
-- * Only the minimal services are implemented


PUS-ST09 DEFINITIONS ::=
BEGIN

  IMPORTS 
  PusUInt32 FROM PUS-TypesDefinitions
  PusTime FROM PUS-Time
  ;
    
  PusSt09ExponentialRate ::= PusUInt32
    
  -- Data for TC[9,1] set time report generation rate
  PusTC-9-1-Data ::= SEQUENCE
  {
    exponentialRate PusSt09ExponentialRate
  }
  
  -- Data for TM[9,2] CUC time report
  PusTM-9-2-Data ::= SEQUENCE
  {
    exponentialRate PusSt09ExponentialRate,
    time PusTime
    -- spacecraft time referenced status
  }
    
END

-- H2020 ESROCOS Project
-- Company: GMV Aerospace & Defence S.A.U.
-- Licence: GPLv2

-- ASN.1 definitions for service ST[12] On-board monitoring
-- (cf. ECSS-E-ST-70-41C sections 6.12, 8.12)
--


--TODO

PUS-ST12 DEFINITIONS ::= 
BEGIN

	
	IMPORTS 
	PusUInt32 FROM PUS-TypesDefinitions
	;
	
	 -- PMON identifier
	PusSt12pmonId ::= PusUInt32
	    
	
	
	-- Data for TC[19,1] and TC[19,2], 
	PusTC-12-1-2-Data  ::= SEQUENCE
	{
		pmonId PusSt12pmonId
	}
    
END

-- H2020 ESROCOS Project
-- Company: GMV Aerospace & Defence S.A.U.
-- Licence: GPLv2

-- ASN.1 definitions for service ST[18] On-board control procedure
-- (cf. ECSS-E-ST-70-41C sections 6.18, 8.18)
--
-- * Only the minimal services are implemented:
-- * OBCP management
-- 	- TC[18,1] Load OBCP Direct                  
--		- TC[18,2] Unload OBCP                      
--		- TC[18,3] Activate OBCP     
--		- TC[18,4] Stop OBCP    
--		- TC[18,5] Suspend OBCP     
--		- TC[18,6] Resume OBCP  
--		- TC[18,12] Abort OBCP    
--		- TC[18,13] Load OBCP by reference  
-- * OBCP engine management
--		- TC[18,21] Start OBCP engine  
--		- TC[18,22] Stop OBCP engine 

--TODO

PUS-ST18 DEFINITIONS ::= 
BEGIN


	IMPORTS 
	PusUInt16, PusUInt32, PusUInt64 FROM PUS-TypesDefinitions
	
	PusSt23RepositoryPath, PusSt23FileName FROM PUS-ST23
	
	PusConfigDummyType, pus-ST18-SIZE-OBCP-ID, pus-ST18-MAX-SIZE-OBCP-CODE, pus-ST18-SIZE-OBCP-CHECKSUM FROM PUS-Config
	;
    
	PusSt18ObcpId ::= OCTET STRING (SIZE(pus-ST18-SIZE-OBCP-ID))
	
	PusSt18ObcpCode ::= OCTET STRING (SIZE(1 .. pus-ST18-MAX-SIZE-OBCP-CODE))
	
	PusSt18ObcpChecksum ::= PusUInt16
	
	PusSt18ObservabilityLevel ::= ENUMERATED
	{
		none(0),
		procedure(1),
		step(2),
		detailed(3)
	}
    
	-- Data TC[18,1]
	PusTC-18-1-Data ::= SEQUENCE
	{
		obcpId		PusSt18ObcpId,
		obcpCode		PusSt18ObcpCode,
		checksum		PusSt18ObcpChecksum -- OPTIONAL
	}
	
	-- Data TC[18,2], TC[18,6], TC[18,12]
	PusTC-18-2-6-12-Data ::= SEQUENCE
	{
		obcpId		PusSt18ObcpId
	}
       
   -- Data TC[18,3]
	PusTC-18-3-Data ::= SEQUENCE
	{
		obcpId		PusSt18ObcpId,
		observabilityLevel PusSt18ObservabilityLevel -- OPTIONAL
		-- argument values deduced --OPTIONAL
	}
	
	-- Data TC[18,4], TC[18,5]
	PusTC-18-4-5-Data ::= SEQUENCE
	{
		obcpId		PusSt18ObcpId,
		stepId		PusUInt32 -- 0 for current step, ENUM?
	}
	

	-- Data TC[18,13]
	PusTC-18-13-Data ::= SEQUENCE
	{
		obcpId		PusSt18ObcpId,
		repository 	PusSt23RepositoryPath, 	-- OPTIONAL
		fileName		PusSt23FileName			-- OPTIONAL
	} 
	
	-- Data TC[18,21]
	-- NONE
	
	-- Data TC[18,22]
	-- NONE
    
END

-- H2020 ESROCOS Project
-- Company: GMV Aerospace & Defence S.A.U.
-- Licence: GPLv2

-- ASN.1 definitions for service ST[19] Event-Action
-- (cf. ECSS-E-ST-70-41C sections 6.19, 8.19)
--
-- Limitations:
-- * Only the minimal services are implemented
--    TC-19-1 Add Event Action Definitions
--    TC-19-2 Delete Event Action Definitions
--    TC-19-4 Enable Event Action Definitions
--    TC-19-5 Disable Event Action Definitions



PUS-ST19 DEFINITIONS ::=
BEGIN

  IMPORTS 
  PusUInt32, PusUInt64 FROM PUS-TypesDefinitions
  PusSt05EventId FROM PUS-ST05
  ;
    
    
    -- Data for TC[19,X] (except for TC[19,1]), event action
  PusTC-19-X-Data ::= SEQUENCE
  {
 -- 	-- Just 1 action-event per TC
 -- 	-- No Aplication Process ID in TC packet
    	eventId PusSt05EventId
  }
    
END

-- H2020 ESROCOS Project
-- Company: GMV Aerospace & Defence S.A.U.
-- Licence: GPLv2

-- ASN.1 definitions for service ST[20] on-board parameter management
-- (cf. ECSS-E-ST-70-41C sections 6.20, 8.20)
--
-- Limitations:
-- * Only the minimal services are implemented, 20.1, 20.2, 20.3


PUS-ST20 DEFINITIONS ::=
BEGIN

    IMPORTS 
    PusUInt32, PusUInt64 FROM PUS-TypesDefinitions
    ;
    
    -- Identifier of on-board parameters
    PusSt20OnBoardParameterId ::= PusUInt32
    
    -- StoredParam of reports
    PusSt20StoredParam ::= PusUInt64
    
    -- Data for TC[20,1], TM[20,2] and TC[20,3], on-board parameter management
    PusTC-TM-20-X-Data ::= SEQUENCE
    {
    	paramId PusSt20OnBoardParameterId,
    	value PusSt20StoredParam
    }
    
END

-- H2020 ESROCOS Project
-- Company: GMV Aerospace & Defence S.A.U.
-- Licence: GPLv2

-- ASN.1 definitions for private service ST[200] Timeline Control
--
-- Several subservices are implemented:
--  - TM[200,2] planner report
 
--  - TC[200,3] mission request
--  - TM[200,4] mission report
 
--  - TC[200,5] hotdockcmd request
--  - TM[200,6] hotdockcmd report

--  - TM[200,8] hotdockstatus report
 
--  - TC[200,9] wmcmd request
--  - TM[200,10] wmcmd report
 
--  - TC[200,11] basecmd request
--  - TM[200,12] basecmd report
 
--  - TC[200,13] efcmd request
--  - TM[200,14] efcmd report


PUS-ST200 DEFINITIONS ::= 
BEGIN

    IMPORTS 
    PusUInt32 FROM PUS-TypesDefinitions T-String FROM TASTE-ExtendedTypes
    Plannerstatus FROM Agent-Trex-to-Taste-Dataview
    Missionstatus FROM Agent-Trex-to-Taste-Dataview
    Hotdockcmdstatus FROM Agent-Trex-to-Taste-Dataview
    Hotdockstatusstatus FROM Agent-Trex-to-Taste-Dataview
    Wmcmdstatus FROM Agent-Trex-to-Taste-Dataview
    Basecmdstatus FROM Agent-Trex-to-Taste-Dataview
    Efcmdstatus FROM Agent-Trex-to-Taste-Dataview
    ;
    
    -- Data for TM[200,2]
    PusTM-200-2-Data ::= SEQUENCE
    {
    	observation Plannerstatus,
        agent T-String
    }
    
     
    -- Data for TC[200,3]
    PusTC-200-3-Data ::= SEQUENCE
    {
    	goal Missionstatus,
        agent T-String
    }
    
    -- Data for TM[200,4]
    PusTM-200-4-Data ::= SEQUENCE
    {
    	observation Missionstatus,
        agent T-String
    }
    
     
    -- Data for TC[200,5]
    PusTC-200-5-Data ::= SEQUENCE
    {
    	goal Hotdockcmdstatus,
        agent T-String
    }
    
    -- Data for TM[200,6]
    PusTM-200-6-Data ::= SEQUENCE
    {
    	observation Hotdockcmdstatus,
        agent T-String
    }
    
    
    -- Data for TM[200,8]
    PusTM-200-8-Data ::= SEQUENCE
    {
    	observation Hotdockstatusstatus,
        agent T-String
    }
    
     
    -- Data for TC[200,9]
    PusTC-200-9-Data ::= SEQUENCE
    {
    	goal Wmcmdstatus,
        agent T-String
    }
    
    -- Data for TM[200,10]
    PusTM-200-10-Data ::= SEQUENCE
    {
    	observation Wmcmdstatus,
        agent T-String
    }
    
     
    -- Data for TC[200,11]
    PusTC-200-11-Data ::= SEQUENCE
    {
    	goal Basecmdstatus,
        agent T-String
    }
    
    -- Data for TM[200,12]
    PusTM-200-12-Data ::= SEQUENCE
    {
    	observation Basecmdstatus,
        agent T-String
    }
    
     
    -- Data for TC[200,13]
    PusTC-200-13-Data ::= SEQUENCE
    {
    	goal Efcmdstatus,
        agent T-String
    }
    
    -- Data for TM[200,14]
    PusTM-200-14-Data ::= SEQUENCE
    {
    	observation Efcmdstatus,
        agent T-String
    }
    

END


--------------------------------------------------------------------------------------
--!  ASN file generated automatically by the ERGO TREX2TASTE interface generator
--!  This file will be overriten if output path given to code generator matches this
--!  path.
--!  I you want to keep changes made to this file keep it safe.
--!  Was generated from configuration file: /home/peraspera/esrocos_workspace/control/mosar_agent/cfg/mosar_timeline.cfg and /home/peraspera/esrocos_workspace/control/mosar_agent/cfg/mosar_domain.cfg 
--!  Date/time of generation: 2020-06-12 12:07:55 
--------------------------------------------------------------------------------------
----------------------------------------------------------------------------------
--!  This file defines the data types that are used to communicate with the Agent
--!  controller.
----------------------------------------------------------------------------------


Agent-Trex-to-Taste-Dataview DEFINITIONS ::=
BEGIN


-- Import of TASTE predefined basic types (TASTE-ExtendedTypes DEFINITIONS)
IMPORTS T-UInt32, T-Boolean, T-Int32 FROM TASTE-BasicTypes T-Double, T-Float, T-Int64, T-UInt16, T-String FROM TASTE-ExtendedTypes;


-- Basic TREX-AGENT types
IntegerIntervalDomain ::= SEQUENCE{
    min   T-Int64,
    max   T-Int64
}

FloatIntervalDomain ::= SEQUENCE{
    min   T-Float,
    max   T-Float
}

EnumDomain ::= SEQUENCE{
    key     T-String,
    value   T-Int64
}

HotdockcmdPred ::= ENUMERATED { hotdockcmd-sendState, hotdockcmd-idle, hotdockcmd-cancel }
HotdockstatusPred ::= ENUMERATED { hotdockstatus-status, hotdockstatus-cancel }
WmcmdPred ::= ENUMERATED { wmcmd-movetohd, wmcmd-movetoslot, wmcmd-idle, wmcmd-cancel }
BasecmdPred ::= ENUMERATED { basecmd-error, basecmd-switchBase, basecmd-baseAt, basecmd-cancel }
EfcmdPred ::= ENUMERATED { efcmd-pick, efcmd-drop, efcmd-idle, efcmd-cancel }
PlannerPred ::= ENUMERATED { planner-fault, planner-idle, planner-planning, planner-cancel }
MissionPred ::= ENUMERATED { mission-place, mission-loadinge3plan, mission-idle, mission-cancel }
AutonomyPred ::= ENUMERATED { autonomy-E1, autonomy-E2, autonomy-E3, autonomy-E4, autonomy-cancel }

-- BOOLD DOMAIN DATA (AGENT-FUNCTIONAL)
Boold ::= SEQUENCE {
    value        T-Int64
    
}

-- INTD DOMAIN DATA (AGENT-FUNCTIONAL)
Intd ::= SEQUENCE {
    value        T-Int64
    
}

-- FLOATD DOMAIN DATA (AGENT-FUNCTIONAL)
Floatd ::= SEQUENCE {
    value        T-Float
    
}

-- STRINGD DOMAIN DATA (AGENT-FUNCTIONAL)
Stringd ::= SEQUENCE {
    value        T-String
    
}

-- INT2D DOMAIN DATA (AGENT-FUNCTIONAL)
Int2d ::= SEQUENCE {
    x        T-Int64,
    y        T-Int64
    
}

-- SLOTID DOMAIN DATA (AGENT-FUNCTIONAL)
Slotid ::= SEQUENCE {
    x        T-Int64,
    y        T-Int64,
    z        T-Int64,
    svc        T-Int64
    
}

-- POSITION3D DOMAIN DATA (AGENT-FUNCTIONAL)
Position3D ::= SEQUENCE {
    x        T-Float,
    y        T-Float
    
}

-- QUATERNIOND DOMAIN DATA (AGENT-FUNCTIONAL)
Quaterniond ::= SEQUENCE {
    x        T-Float,
    y        T-Float
    
}
 


-- HOTDOCKCMD TIMELINE DATA (AGENT-FUNCTIONAL)
Hotdockcmdstatus ::= SEQUENCE {
    predicate       HotdockcmdPred,
    inittime        IntegerIntervalDomain,
    endtime        IntegerIntervalDomain,
    sm        EnumDomain,
    hotdock        Stringd,
    statehd        EnumDomain,
    status        EnumDomain
    
}

-- HOTDOCKSTATUS TIMELINE DATA (AGENT-FUNCTIONAL)
Hotdockstatusstatus ::= SEQUENCE {
    predicate       HotdockstatusPred,
    inittime        IntegerIntervalDomain,
    endtime        IntegerIntervalDomain,
    pathfile        Stringd
    
}

-- WMCMD TIMELINE DATA (AGENT-FUNCTIONAL)
Wmcmdstatus ::= SEQUENCE {
    predicate       WmcmdPred,
    inittime        IntegerIntervalDomain,
    endtime        IntegerIntervalDomain,
    hotdock        Stringd,
    slot        Slotid,
    face        Stringd,
    yaw        EnumDomain,
    status        EnumDomain
    
}

-- BASECMD TIMELINE DATA (AGENT-FUNCTIONAL)
Basecmdstatus ::= SEQUENCE {
    predicate       BasecmdPred,
    inittime        IntegerIntervalDomain,
    endtime        IntegerIntervalDomain,
    hotdock        Stringd
    
}

-- EFCMD TIMELINE DATA (AGENT-FUNCTIONAL)
Efcmdstatus ::= SEQUENCE {
    predicate       EfcmdPred,
    inittime        IntegerIntervalDomain,
    endtime        IntegerIntervalDomain,
    hotdock        Stringd,
    status        EnumDomain
    
}

-- PLANNER TIMELINE DATA (AGENT-FUNCTIONAL)
Plannerstatus ::= SEQUENCE {
    predicate       PlannerPred,
    inittime        IntegerIntervalDomain,
    endtime        IntegerIntervalDomain,
    goals        Intd
    
}

-- MISSION TIMELINE DATA (AGENT-FUNCTIONAL)
Missionstatus ::= SEQUENCE {
    predicate       MissionPred,
    inittime        IntegerIntervalDomain,
    endtime        IntegerIntervalDomain,
    sm        Stringd,
    slot        Stringd,
    orientation        Stringd,
    file        Stringd
    
}

-- AUTONOMY TIMELINE DATA (AGENT-FUNCTIONAL)
Autonomystatus ::= SEQUENCE {
    predicate       AutonomyPred,
    inittime        IntegerIntervalDomain,
    endtime        IntegerIntervalDomain
    
}
 


-- ASN.1 Type definitions must start with an uppercase
-- Field names in records (SEQUENCE) must start with a lowercase
-- Underscores are not allowed: use dash (hyphen) 

END

-- H2020 ESROCOS Project
-- Company: GMV Aerospace & Defence S.A.U.
-- Licence: GPLv2

-- ASN.1 definitions for service ST[220] Reconfiguration
--
-- Limitations:
-- * This is part of a prototype for a demonstration


PUS-ST220 DEFINITIONS ::=
BEGIN

    IMPORTS
    PusUInt32, PusInt32  FROM PUS-TypesDefinitions
    PusSt03ParameterId, PusSt03HousekeepingReportId FROM PUS-ST03
    ;

    Pus-220-StateId ::= ENUMERATED { 
        idle(0), mode1(1), mode2(2)
    }
    
   
    -- Data for TC[220,1]
    PusTC-220-1-Data ::= SEQUENCE
    {
    	targetState Pus-220-StateId
    }

    -- No Data for TC[220,2]

    -- Data for TM[220,3]
    PusTM-220-3-Data ::= SEQUENCE
    {
    	actual Pus-220-StateId
    }


    -- Identification of activable parts
    pus-St220-Parameter-Active PusSt03ParameterId ::= 10

    pus-St220-SM-DMS-Base					PusSt03ParameterId ::= 100
    pus-St220-SM-PWS-Base					PusSt03ParameterId ::= 200
    pus-St220-SM-THS-Base					PusSt03ParameterId ::= 300
    pus-St220-SM-BAT-Base					PusSt03ParameterId ::= 400
    pus-St220-SM-OSP-Base					PusSt03ParameterId ::= 500

    Pus-220-ActiveIds ::= SEQUENCE (SIZE(0 .. 256)) OF PusSt03ParameterId
    pus-St220-SMS Pus-220-ActiveIds ::= {
        pus-St220-SM-DMS-Base, 
        pus-St220-SM-PWS-Base, 
        pus-St220-SM-THS-Base, 
        pus-St220-SM-BAT-Base, 
        pus-St220-SM-OSP-Base
    }
    
    -- Fake power reserve report
    pus-ST03-POWERRESERVE-HK-REPORT PusSt03HousekeepingReportId ::= 400 
    

END

-- H2020 ESROCOS Project
-- Company: GMV Aerospace & Defence S.A.U.
-- Licence: GPLv2

-- ASN.1 definitions for service ST[23] File management
-- (cf. ECSS-E-ST-70-41C sections 6.23, 8.23)

-- * Only the minimal services are implemented:
-- * File handling
--	 - TC-23-1 createFile
--   - TC-23-2 deleteFile
--   - TC-23-3 reportFileAttributes
--   - TM-23-4 reportFileAttributes
-- * File copy
--   - TC-23-14 copyFile

PUS-ST23 DEFINITIONS ::= 
BEGIN

	
	IMPORTS 
	PusUInt64 FROM PUS-TypesDefinitions
	
	PusConfigDummyType, pus-ST23-MAX-SIZE-FILE-PATH,
	pus-ST23-MAX-SIZE-REPOSITORY-PATH, pus-ST23-MAX-SIZE-REPOSITORY-DOMAIN FROM PUS-Config
	;
    
	PusSt23RepositoryPath ::= OCTET STRING (SIZE(1..pus-ST23-MAX-SIZE-REPOSITORY-PATH)) 
	
	PusSt23FileName ::= OCTET STRING (SIZE(1..pus-ST23-MAX-SIZE-FILE-PATH))
	
	PusSt23RepositoryDomain ::= OCTET STRING (SIZE(1..pus-ST23-MAX-SIZE-REPOSITORY-DOMAIN))
    
	-- Data TC[23,1] TM[23,4]
	PusTC-TM-23-1-4-Data ::= SEQUENCE
	{
		repository			PusSt23RepositoryPath,
		fileName			PusSt23FileName,
		maxSize	 			PusUInt64
		-- file locked status BOOLEAN (optional)
		-- additional file atributes DEDUCED (optinal N-Times)
	}
	 
	-- Data TC[23,2] TC[23,3]
	PusTC-23-2-3-Data ::= SEQUENCE
	{
		repository			PusSt23RepositoryPath,
		fileName			PusSt23FileName
	}


	-- Data TC[23,14]
	PusTC-23-14-Data ::= SEQUENCE
	{
		sourceRepository  		PusSt23RepositoryPath,
		sourceFileName			PusSt23FileName,
		targetRepository		PusSt23RepositoryPath,
		targetFileName			PusSt23FileName
	}
	
	
END

TASTE-ExtendedTypes DEFINITIONS ::=
BEGIN

IMPORTS 
T-Int32, T-UInt32, T-Int8, T-UInt8, T-Boolean  FROM TASTE-BasicTypes;

-- Set of TASTE predefined basic types

T-Double ::= REAL (-1.7976931348623157e+308..1.7976931348623157E308)

T-Float ::= REAL (-3.402823466E+38..3.402823466e+38)

T-Int16 ::= INTEGER (-32768..32767 )

T-UInt16 ::= INTEGER (0 .. 65535 )

T-UInt64 ::= INTEGER (0..18446744073709551615)

T-Int64 ::= INTEGER (-9223372036854775808.. 9223372036854775807)

T-String ::= T-StringP{numT-String}

T-StringP{T-UInt32: maxT-String} ::= OCTET STRING (SIZE(0..maxT-String))

numT-String T-UInt32::= 40

T-Time ::= SEQUENCE
{
    secs  T-UInt32,
    nsecs T-UInt32
}
  
END


-- H2020 ESROCOS Project
-- Company: GMV Aerospace & Defence S.A.U.
-- Licence: GPLv2

-- ASN.1 definitions for the time types used in PUS packets
-- (cf. ECSS-E-ST-70-41C)

-- The PUS implementation is normally tailored using the CUC and CDS 
-- time formats defined in CCSDS 301.0-B-4.
--
-- However, this implementation is not concerned with the encoding 
-- details. Instead, a time type similar to the Linux implementation of
-- timespec in <time.h>. This structure contains the fields:
--
--      time_t  tv_sec    Seconds
--      long    tv_nsec   Nanoseconds
--
-- It is the structure returned by clock_gettime.


PUS-Time DEFINITIONS ::=
BEGIN

    IMPORTS PusInt64 FROM PUS-TypesDefinitions;

    -- Time type, based on C timespec <time.h>
    -- For absolute times, it indicates the time from the epoch 1970-01-01 00:00:00 +0000 (UTC)
    PusTime ::= SEQUENCE
    {
        tv-sec  PusInt64,
        tv-nsec PusInt64
    }

END

-- H2020 ESROCOS Project
-- Company: GMV Aerospace & Defence S.A.U.
-- Licence: GPLv2

-- ASN.1 definitions for small N-bit integers and types used in PUS packets

PUS-TypesDefinitions DEFINITIONS ::=
BEGIN

	PusUInt3  ::= INTEGER (0 .. 7)
	PusUInt4  ::= INTEGER (0 .. 15)
	PusUInt8  ::= INTEGER (0 .. 255)
	PusUInt11 ::= INTEGER (0 .. 2047)
	PusUInt14 ::= INTEGER (0 .. 16383)
	PusUInt16 ::= INTEGER (0 .. 65535)
	PusUInt32 ::= INTEGER (0 .. 4294967295)
	PusUInt64 ::= INTEGER (0 .. 18446744073709551615)
	
	PusInt32 ::= INTEGER (-2147483648 .. 2147483647)
	PusInt64 ::= INTEGER (-9223372036854775808 .. 9223372036854775807)
	
	PusDouble ::= REAL (-1.7976931348623157e+308..1.7976931348623157E308)
	
	PusMemAddr ::= PusUInt64

END

TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

END

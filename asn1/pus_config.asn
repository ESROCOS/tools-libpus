-- H2020 ESROCOS Project
-- Company: GMV Aerospace & Defence S.A.U.
-- Licence: GPLv2

-- ASN.1 constant definitions related to the configuration of PUS services
--
-- This file centralizes some definitions regarding sizes, etc. of the PUS services.
-- 
-- Limitations:
-- These sizes could be derived from the mission configuration. However, in order to 
-- simplify code generation, they are currently defined here.


PUS-Config DEFINITIONS ::=
BEGIN

    IMPORTS 
    PusUInt32 FROM PUS-TypesDefinitions
    ;
    
    -- Dummy type, workaround for missing include bug in asn1.exe (TO-DO: remove when fixed)
    PusConfigDummyType ::= PusUInt32

    -- Maximum number of parameters in a housekeeping report
    pus-ST03-MAX-REPORT-LENGTH PusUInt32 ::= 20
    
    -- Maximun number of Scheduled Actions in a TC11.4 packet
    pus-ST11-MAX-SCHEDULED-ACTIVITIES PusUInt32 ::= 5
    
    -- Maximun number of character in OBCP ID (ST18)
    pus-ST18-SIZE-OBCP-ID PusUInt32 ::= 10
    
    -- Maximun number of character in OBCP Code TC[18,1] 
    pus-ST18-MAX-SIZE-OBCP-CODE PusUInt32 ::= 15000
    
    -- Maximun number of bits in OBCP CHECKSUM (ST18)
    pus-ST18-SIZE-OBCP-CHECKSUM PusUInt32 ::= 16
    
    -- Maximum number of character in file path (ST23)
    pus-ST23-MAX-SIZE-FILE-PATH PusUInt32 ::= 30
    
    -- Maximum number of character in repository path (ST23)
    pus-ST23-MAX-SIZE-REPOSITORY-PATH PusUInt32 ::= 30
    
    -- Maximum number of character in repository domain (ST23)
    pus-ST23-MAX-SIZE-REPOSITORY-DOMAIN PusUInt32 ::= 30
    
    -- Maximum size of a file in ST23
    pus-ST23-MAX-SIZE-FILE PusUInt32 ::= 1000

END

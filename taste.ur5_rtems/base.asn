Base-Types DEFINITIONS ::=
BEGIN

IMPORTS T-UInt32, T-Boolean, T-Int32 FROM TASTE-BasicTypes T-Double, T-Float, T-Int64, T-UInt16, T-String FROM TASTE-ExtendedTypes DummyBase-T, numBase-JointTrajectory, numStd-orogen-typekits-mtype-std-vector-base-JointTransform, numStd-orogen-typekits-mtype-std-vector-base-Wrench, numStd-vector-Wrappers-Vector4d, numStd-orogen-typekits-mtype-std-vector-base-Trajectory, numBase-JointLimits-names, numBase-JointLimits-elements, numBase-JointsTrajectory-names, numBase-JointsTrajectory-elements, numBase-JointsTrajectory-times-val, numBase-NamedVector-Base-JointLimitRange-names, numBase-NamedVector-Base-JointLimitRange-elements, numBase-NamedVector-Base-JointState-names, numBase-NamedVector-Base-Wrench-names, numBase-NamedVector-Base-Wrench-elements, numBase-NamedVector-Base-JointTrajectory-names, numBase-NamedVector-Base-JointTrajectory-elements, numBase-samples-DepthMap-timestamps, numBase-samples-DepthMap-vertical-interval, numBase-samples-DepthMap-horizontal-interval, numBase-samples-DepthMap-distances, numBase-samples-DepthMap-remissions, numBase-samples-DistanceImage-data, numBase-commands-Joints-names, numBase-samples-LaserScan-ranges, numBase-samples-LaserScan-remission, numBase-samples-Pointcloud-points, numBase-samples-Pointcloud-colors, numBase-samples-Sonar-timestamps, numBase-samples-Sonar-bearings, numBase-samples-Sonar-bins, numBase-samples-SonarBeam-beam, numBase-samples-SonarScan-data, numBase-samples-SonarScan-time-beams, numBase-samples-Wrenches-names, numBase-samples-Wrenches-elements, numBase-JointTransformVector-names, numBase-JointTransformVector-elements, numBase-NamedVector-Base-JointTransform-names, numBase-NamedVector-Base-JointTransform-elements, numBase-samples-frame-Frame-image, numBase-samples-frame-Frame-attributes, numWrappers-MatrixXd-data, numWrappers-VectorXd-data, numBase-JointTransformVector-m-names, numBase-NamedVector-base-JointTransform-m-names, numBase-NamedVector-base-Wrench-m-names, numBase-samples-Pointcloud-m-points, numBase-samples-Pointcloud-m-colors, numBase-samples-Wrenches-m-names, numWrappers-geometry-Spline-knots, numWrappers-geometry-Spline-vertices FROM UserDefs-Base-Types;

--Definition Dummy2Base-T starts
    Dummy2Base-T ::= DummyBase-T
-- Definition Dummy2Base-T ends

--Definition Base-JointState-MODE starts
Base-JointState-MODE ::= ENUMERATED
{
    base-jointstate-mode-acceleration,
    base-jointstate-mode-effort,
    base-jointstate-mode-position,
    base-jointstate-mode-raw,
    base-jointstate-mode-speed,
    base-jointstate-mode-unset
}
-- Definition Base-JointState-MODE ends

--Definition Base-JointTrajectoryP starts
Base-JointTrajectoryP {T-UInt32: maxBase-JointTrajectory} ::= SEQUENCE(SIZE(1..maxBase-JointTrajectory)) OF Base-JointState
-- Definition Base-JointTrajectoryP ends

--Definition Base-JointTrajectory starts
Base-JointTrajectory ::= Base-JointTrajectoryP{numBase-JointTrajectory}
-- Definition Base-JointTrajectory ends

--Definition Base-Pose starts
Base-Pose ::= SEQUENCE
{
    position  Wrappers-Vector3d,
    orientation  Wrappers-Quaterniond
}
-- Definition Base-Pose ends

--Definition Base-JointState starts
Base-JointState ::= SEQUENCE
{
    position  T-Double,
    speed  T-Float,
    effort  T-Float,
    raw  T-Float,
    acceleration  T-Float
}
-- Definition Base-JointState ends

--Definition Base-Time starts
Base-Time ::= SEQUENCE
{
    microseconds  T-Int64
}
-- Definition Base-Time ends

--Definition Base-JointsTrajectoryP starts
Base-JointsTrajectoryP{T-UInt32: maxBase-JointsTrajectory-names, T-UInt32: maxBase-JointsTrajectory-elements, T-UInt32: maxBase-JointsTrajectory-times-val} ::= SEQUENCE
{
    names  SEQUENCE (SIZE(1..maxBase-JointsTrajectory-names)) OF T-String,
    elements  SEQUENCE (SIZE(1..maxBase-JointsTrajectory-elements)) OF Base-JointTrajectory,
    times-val  SEQUENCE (SIZE(1..maxBase-JointsTrajectory-times-val)) OF Base-Time
}
-- Definition Base-JointsTrajectoryP ends

--Definition Base-JointsTrajectory starts
Base-JointsTrajectory ::= Base-JointsTrajectoryP{numBase-JointsTrajectory-names, numBase-JointsTrajectory-elements, numBase-JointsTrajectory-times-val}
-- Definition Base-JointsTrajectory ends


--Definition Base-commands-JointsP starts
Base-commands-JointsP{T-UInt32: maxBase-commands-Joints-names} ::= SEQUENCE
{
    names  SEQUENCE (SIZE(1..maxBase-commands-Joints-names)) OF T-String,
    elements  Base-JointTrajectory,
    time  Base-Time
}
-- Definition Base-commands-JointsP ends

--Definition Base-commands-Joints starts
Base-commands-Joints ::= Base-commands-JointsP{numBase-commands-Joints-names}
-- Definition Base-commands-Joints ends

--Definition Wrappers-Vector3d starts
Wrappers-Vector3d ::= SEQUENCE
{
    data  SEQUENCE(SIZE(1..3)) OF T-Double
}
-- Definition Wrappers-Vector3d ends


--Definition Wrappers-Quaterniond starts
Wrappers-Quaterniond ::= SEQUENCE
{
    im  SEQUENCE(SIZE(1..3)) OF T-Double,
    re  T-Double
}
-- Definition Wrappers-Quaterniond ends

--Definition Wrappers-Matrix3d starts
Wrappers-Matrix3d ::= SEQUENCE
{
    data  SEQUENCE(SIZE(1..9)) OF T-Double
}
-- Definition Wrappers-Matrix3d ends


--Definition Base-samples-RigidBodyState starts
Base-samples-RigidBodyState ::= SEQUENCE
{
    time  Base-Time,
    sourceframe  T-String,
    targetframe  T-String,
    position  Wrappers-Vector3d,
    cov-position  Wrappers-Matrix3d,
    orientation  Wrappers-Quaterniond,
    cov-orientation  Wrappers-Matrix3d,
    velocity  Wrappers-Vector3d,
    cov-velocity  Wrappers-Matrix3d,
    angular-velocity  Wrappers-Vector3d,
    cov-angular-velocity  Wrappers-Matrix3d
}
-- Definition Base-samples-RigidBodyState ends

--Definition Wrappers-VectorXdP starts
Wrappers-VectorXdP{T-UInt32: maxWrappers-VectorXd-data} ::= SEQUENCE
{
    data  SEQUENCE (SIZE(1..maxWrappers-VectorXd-data)) OF T-Double
}
-- Definition Wrappers-VectorXdP ends

--Definition Wrappers-VectorXd starts
Wrappers-VectorXd ::= Wrappers-VectorXdP{numWrappers-VectorXd-data}
-- Definition Wrappers-VectorXd ends

--Definition Wrappers-MatrixXdP starts
Wrappers-MatrixXdP{T-UInt32: maxWrappers-MatrixXd-data} ::= SEQUENCE
{
    rows  T-Int32,
    cols  T-Int32,
    data  SEQUENCE (SIZE(1..maxWrappers-MatrixXd-data)) OF T-Double
}
-- Definition Wrappers-MatrixXdP ends

--Definition Wrappers-MatrixXd starts
Wrappers-MatrixXd ::= Wrappers-MatrixXdP{numWrappers-MatrixXd-data}
-- Definition Wrappers-MatrixXd ends

END

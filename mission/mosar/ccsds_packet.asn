-- H2020 ESROCOS Project
-- Company: GMV Aerospace & Defence S.A.U.
-- Licence: GPLv2

-- ASN.1 definitions for CCSDS packets
-- (cf. ECSS-E-ST-70-41C section 7.4)

PUS-CcsdsPacket DEFINITIONS ::=
BEGIN

	IMPORTS 
	PusTime FROM PUS-Time
	
	PusServiceType, PusSubserviceType FROM PUS-Services
	
	PusVersionNumber, PusTimeReferenceStatus, PusMessageTypeCounter, PusPacketType, PusApid, 
	PusChecksum, PusAcknowledgementFlags, PusPacketVersion, PusSecondaryHeaderFlag, PusSequenceFlags, 
	PusSequenceCount, PusPacketDataLength FROM PUS-CcsdsPacketFields

	PusTM-1-X-Data FROM PUS-ST01
	PusTM-3-25-Data, PusTC-3-5-Data, PusTC-3-6-Data FROM PUS-ST03
	PusTM-5-X-Data FROM PUS-ST05
	PusTC-8-1-Data FROM PUS-ST08
	PusTC-9-1-Data, PusTM-9-2-Data FROM PUS-ST09
	PusTC-12-1-2-Data  FROM PUS-ST12
	PusTC-19-X-Data FROM PUS-ST19
	PusTC-TM-20-X-Data FROM PUS-ST20
  	
	PusTC-18-1-Data, PusTC-18-2-6-12-Data, PusTC-18-3-Data, 
	PusTC-18-4-5-Data, PusTC-18-13-Data FROM PUS-ST18
	
	PusTC-TM-23-1-4-Data, PusTC-23-2-3-Data, PusTC-23-14-Data FROM PUS-ST23
  	
  	PusSt05EventId FROM PUS-ST05 -- for PusTC-19-X-Data
  	
  	PusUInt32 FROM PUS-TypesDefinitions
  	
  	pus-ST11-MAX-SCHEDULED-ACTIVITIES FROM PUS-Config
    PusTM-200-18-Data FROM PUS-ST200 --  planner  
     
    PusTC-200-19-Data, PusTM-200-20-Data FROM PUS-ST200 --  mission  
     
    PusTC-200-13-Data, PusTM-200-14-Data FROM PUS-ST200 --  sodmission  
     
    PusTC-200-1-Data, PusTM-200-2-Data FROM PUS-ST200 --  hotdockcmd  
    PusTM-200-4-Data FROM PUS-ST200 --  hotdockstatus  
     
    PusTC-200-5-Data, PusTM-200-6-Data FROM PUS-ST200 --  wmcmd  
     
    PusTC-200-9-Data, PusTM-200-10-Data FROM PUS-ST200 --  basecmd  
     
    PusTC-200-11-Data, PusTM-200-12-Data FROM PUS-ST200 --  efcmd  
    PusTM-200-8-Data FROM PUS-ST200 --  wmstatus  
    PusTM-200-16-Data FROM PUS-ST200 --  sodplanner  
    
/* R_ICU_SPW_PNP */
    PusTC-210-1-Data FROM PUS-ST210                     --  SpW Routing Table Set Entry
    PusTC-210-2-Data FROM PUS-ST210                     --  SpW PnP Set Owner Fields
/* R_ICU */
    PusTC-210-11-Data FROM PUS-ST210                     --  Configure Time Epoch
    PusTC-210-12-Data FROM PUS-ST210                     --  Set LEDs
/* HOTDOCK */
    PusTC-210-21-Data FROM PUS-ST210                     --  Set Houskeeping Data Rate
    PusTC-210-22-Data FROM PUS-ST210                     --  Go to state
    PusTC-210-23-Data FROM PUS-ST210                     --  Command P15V Line
    PusTC-210-24-Data FROM PUS-ST210                     --  Command P2V5 Line
    PusTC-210-25-Data FROM PUS-ST210                     --  Coomdad Relay
    PusTC-210-26-Data FROM PUS-ST210                     --  Set LVDS Pins
    PusTC-210-27-Data FROM PUS-ST210                     --  Power On Off Motor
    PusTC-210-28-Data FROM PUS-ST210                     --  Set Motor Speed
    PusTC-210-29-Data FROM PUS-ST210                     --  Set Motor Direction
    PusTC-210-30-Data FROM PUS-ST210                     --  Set Motor Current Limit
    PusTC-210-31-Data FROM PUS-ST210                     --  Calibrate Controller
    PusTC-210-32-Data FROM PUS-ST210                     --  Reset Controller
/* OSP */
    PusTC-210-41-Data FROM PUS-ST210                     --  OSP Control Command
    PusTC-210-42-Data FROM PUS-ST210                     --  Capture Image
/* BAT */
    PusTC-210-61-Data FROM PUS-ST210                     --  HK1 Request
    PusTC-210-62-Data FROM PUS-ST210                     --  HK2 Request
    PusTC-210-63-Data FROM PUS-ST210                     --  All HK Request
    PusTC-210-64-Data FROM PUS-ST210                     --  Go to state
    PusTC-210-65-Data FROM PUS-ST210                     --  Command 48V converter
    PusTC-210-66-Data FROM PUS-ST210                     --  Command Bat charger 
/* WM */
    PusTC-210-71-Data FROM PUS-ST210                     --  Mode Command
    PusTC-210-72-Data FROM PUS-ST210                     --  Control Mode Command
    PusTC-210-73-Data FROM PUS-ST210                     --  Move Cartesian Trajectory
/* THS */
    PusTC-210-81-Data FROM PUS-ST210                     --  Mode Command
    PusTC-210-82-Data FROM PUS-ST210                     --  Components Command
/* CPDU */
    PusTC-210-91-Data FROM PUS-ST210                     --  Specific HK Request
    PusTC-210-92-Data FROM PUS-ST210                     --  All HK Request
    PusTC-210-93-Data FROM PUS-ST210                     --  Command Switch 1
    PusTC-210-94-Data FROM PUS-ST210                     --  Command 24V Converter A
    PusTC-210-95-Data FROM PUS-ST210                     --  SM Power Off

    PusTC-220-1-Data, PusTM-220-3-Data FROM PUS-ST220   --  reconfiguration
  	;

    -- dummy data field for packets with no data
    PusTM-TC-Dummy-Data ::= PusUInt32

    -- TM secondary header
    PusTmHeader ::= SEQUENCE
    {
        pusVersion      PusVersionNumber,
        timeRefStatus   PusTimeReferenceStatus,
        serviceId       PusServiceType,
        subtypeId       PusSubserviceType,
        msgTypeCount    PusMessageTypeCounter,
        destination     PusApid,
        time            PusTime
        -- no spare bits
    }
    
    -- TM actual data
    PusTmSourceData ::= CHOICE
    {
        st-0-0  PusTM-TC-Dummy-Data,
        st-1-X 	PusTM-1-X-Data,
        st-3-25 PusTM-3-25-Data,
        st-5-X 	PusTM-5-X-Data,
        st-9-2 	PusTM-9-2-Data,
        st-20-2 PusTC-TM-20-X-Data,
        st-23-4 PusTC-TM-23-1-4-Data,
        st-200-18 PusTM-200-18-Data, 
        st-200-20 PusTM-200-20-Data, 
        st-200-14 PusTM-200-14-Data, 
        st-200-2 PusTM-200-2-Data, 
        st-200-4 PusTM-200-4-Data, 
        st-200-6 PusTM-200-6-Data, 
        st-200-10 PusTM-200-10-Data, 
        st-200-12 PusTM-200-12-Data, 
        st-200-8 PusTM-200-8-Data, 
        st-200-16 PusTM-200-16-Data,
	st-220-3 PusTM-220-3-Data
    }
    
    -- TC secondary header
    PusTcHeader ::= SEQUENCE
    {
        pusVersion      PusVersionNumber,
        ackFlags        PusAcknowledgementFlags,
        serviceId       PusServiceType,
        subtypeId       PusSubserviceType,
        source          PusApid
        -- no spare bits
    }
    
    
    -- Data for TM[19,1], event action
    PusTC-19-1-Data  ::= SEQUENCE
    {
    	-- Just 1 action-event per TC
    	-- No Aplication Process ID in TC packet
    	eventId 		PusSt05EventId,
    	packetReduced 	PusPacketReduced
    }
    
    -- Schedulable action TC11.4
    PusTcScheduledActivity ::= SEQUENCE
    {	
    	time			PusTime,
    	packetReduced 	PusPacketReduced
    }
    
    -- Data field for TC11.4
    PusTC-11-4-Data ::= SEQUENCE SIZE(1..pus-ST11-MAX-SCHEDULED-ACTIVITIES) OF PusTcScheduledActivity
           
    
    -- TC actual data
    PusTcApplicationData ::= CHOICE
    { -- The same order as the reduced
        st-0-0      PusTM-TC-Dummy-Data,
        st-3-5      PusTC-3-5-Data,
        st-3-6      PusTC-3-6-Data,
    	st-8-1 		PusTC-8-1-Data,
    	st-9-1 		PusTC-9-1-Data,
    	st-12-1-2 	PusTC-12-1-2-Data,
    	st-18-2-6-12 PusTC-18-2-6-12-Data,
    	st-18-3		PusTC-18-3-Data,
    	st-18-4-5	PusTC-18-4-5-Data,
    	st-18-13 	PusTC-18-13-Data,
    	st-19-X 	PusTC-19-X-Data,
    	st-20-X 	PusTC-TM-20-X-Data,
    	st-23-1		PusTC-TM-23-1-4-Data,
    	st-23-2-3	PusTC-23-2-3-Data,
    	st-23-14	PusTC-23-14-Data, 
        st-200-19 PusTC-200-19-Data, 
        st-200-13 PusTC-200-13-Data, 
        st-200-1 PusTC-200-1-Data, 
        st-200-5 PusTC-200-5-Data, 
        st-200-9 PusTC-200-9-Data, 
        st-200-11 PusTC-200-11-Data,

        /* R_ICU_SPW_PNP */
        st-210-1   PusTC-210-1-Data,
        st-210-2   PusTC-210-2-Data,
        /* R_ICU */
        st-210-11   PusTC-210-11-Data,
        st-210-12   PusTC-210-12-Data,
        /* HOTDOCK */
        st-210-21   PusTC-210-21-Data,
        st-210-22   PusTC-210-22-Data,
        st-210-23   PusTC-210-23-Data,
        st-210-24   PusTC-210-24-Data,
        st-210-25   PusTC-210-25-Data,
        st-210-26   PusTC-210-26-Data,
        st-210-27   PusTC-210-27-Data,
        st-210-28   PusTC-210-28-Data,
        st-210-29   PusTC-210-29-Data,
        st-210-30   PusTC-210-30-Data,
        st-210-31   PusTC-210-31-Data,
        st-210-32   PusTC-210-32-Data,
        /* OSP */
        st-210-41   PusTC-210-41-Data,
        st-210-42   PusTC-210-42-Data,
        /* BAT */
        st-210-61   PusTC-210-61-Data,
        st-210-62   PusTC-210-62-Data,
        st-210-63   PusTC-210-63-Data,
        st-210-64   PusTC-210-64-Data,
        st-210-65   PusTC-210-65-Data,
        st-210-66   PusTC-210-66-Data,
        /* WM */
        st-210-71   PusTC-210-71-Data,
        st-210-72   PusTC-210-72-Data,
        st-210-73   PusTC-210-73-Data,
        /* THS */
        st-210-81   PusTC-210-81-Data,
        st-210-82   PusTC-210-82-Data,
        /* CPDU */
        st-210-91   PusTC-210-91-Data,
        st-210-92   PusTC-210-92-Data,
        st-210-93   PusTC-210-93-Data,
        st-210-94   PusTC-210-94-Data,
        st-210-95   PusTC-210-95-Data,

        st-220-1 PusTC-220-1-Data,
        -- No packet reduced
    	st-11-4 	PusTC-11-4-Data,
    	st-18-1 	PusTC-18-1-Data,
    	st-19-1 	PusTC-19-1-Data
    }
    
    PusTcApplicationDataReduced ::= CHOICE
    {
        st-0-0      PusTM-TC-Dummy-Data,
        st-3-5      PusTC-3-5-Data,
        st-3-6      PusTC-3-6-Data,
    	st-8-1 		PusTC-8-1-Data,
    	st-9-1 		PusTC-9-1-Data,
    	st-12-1-2 	PusTC-12-1-2-Data,
    	st-18-2-6-12 PusTC-18-2-6-12-Data,
    	st-18-3		PusTC-18-3-Data,
    	st-18-4-5	PusTC-18-4-5-Data,
    	st-18-13 	PusTC-18-13-Data,
    	st-19-X 	PusTC-19-X-Data,
    	st-20-X 	PusTC-TM-20-X-Data,
    	st-23-1		PusTC-TM-23-1-4-Data,
    	st-23-2-3	PusTC-23-2-3-Data,
    	st-23-14	PusTC-23-14-Data,
        st-200-19 PusTC-200-19-Data,
        st-200-13 PusTC-200-13-Data,
        st-200-1 PusTC-200-1-Data,
        st-200-5 PusTC-200-5-Data,
        st-200-9 PusTC-200-9-Data,
        st-200-11 PusTC-200-11-Data,

        /* R_ICU_SPW_PNP */
        st-210-1   PusTC-210-1-Data,
        st-210-2   PusTC-210-2-Data,
        /* R_ICU */
        st-210-11   PusTC-210-11-Data,
        st-210-12   PusTC-210-12-Data,
        /* HOTDOCK */
        st-210-21   PusTC-210-21-Data,
        st-210-22   PusTC-210-22-Data,
        st-210-23   PusTC-210-23-Data,
        st-210-24   PusTC-210-24-Data,
        st-210-25   PusTC-210-25-Data,
        st-210-26   PusTC-210-26-Data,
        st-210-27   PusTC-210-27-Data,
        st-210-28   PusTC-210-28-Data,
        st-210-29   PusTC-210-29-Data,
        st-210-30   PusTC-210-30-Data,
        st-210-31   PusTC-210-31-Data,
        st-210-32   PusTC-210-32-Data,
        /* OSP */
        st-210-41   PusTC-210-41-Data,
        st-210-42   PusTC-210-42-Data,
        /* BAT */
        st-210-61   PusTC-210-61-Data,
        st-210-62   PusTC-210-62-Data,
        st-210-63   PusTC-210-63-Data,
        st-210-64   PusTC-210-64-Data,
        st-210-65   PusTC-210-65-Data,
        st-210-66   PusTC-210-66-Data,
        /* WM */
        st-210-71   PusTC-210-71-Data,
        st-210-72   PusTC-210-72-Data,
        st-210-73   PusTC-210-73-Data,
        /* THS */
        st-210-81   PusTC-210-81-Data,
        st-210-82   PusTC-210-82-Data,
        /* CPDU */
        st-210-91   PusTC-210-91-Data,
        st-210-92   PusTC-210-92-Data,
        st-210-93   PusTC-210-93-Data,
        st-210-94   PusTC-210-94-Data,
        st-210-95   PusTC-210-95-Data,

        st-220-1 PusTC-220-1-Data
    }
    
    -- TM/TC header + data
    PusTmHeaderData ::= SEQUENCE
    {
       header  PusTmHeader,
        data    PusTmSourceData
    }
    PusTcHeaderDataTemplate{T} ::= SEQUENCE
    {
        header  PusTcHeader,
        data    T
    }
    
   -- PusTcHeaderData ::= PusTcHeaderDataTemplate{PusTcApplicationData}
   -- PusTcHeaderDataReduced ::= PusTcHeaderDataTemplate{PusTcApplicationDataReduced}


    -- Packet data
    PusPacketDataTemplate{T} ::= CHOICE
    {
        tmData          PusTmHeaderData,
        tmDataNoHeader  PusTmSourceData,
        tcData          PusTcHeaderDataTemplate{T},
        tcDataNoHeader  T
    }
    PusPacketData ::= PusPacketDataTemplate{PusTcApplicationData}
    PusPacketDataReduced ::= PusPacketDataTemplate{PusTcApplicationDataReduced}
    

    -- CCSDS packet
    -- TM/TC user data contains only the source/application data. No spare bits or checksum is used.
    -- Spare bits are not needed because TASTE handles the packing of the fields.
    -- Checksum is not used because TASTE handles encoding/decoding, and there might be 
    -- mismatched checksums if a message is transmitted between hosts with different endianness. 
    PusPacketTemplate{T} ::= SEQUENCE
    {
        packetVersion       PusPacketVersion,
        packetType          PusPacketType,
        secondaryHeaderFlag PusSecondaryHeaderFlag,
        apid                PusApid,
        sequenceFlags       PusSequenceFlags,
        sequenceCount       PusSequenceCount,
        dataLength          PusPacketDataLength,
        data                T
    }
    
    PusPacket ::= PusPacketTemplate {PusPacketData}
	PusPacketReduced ::= PusPacketTemplate {PusPacketDataReduced}


END

----------------------------------------------------------------------------------
--!  This file defines the data types that are used to communicate with the Agent
--!  controller.
----------------------------------------------------------------------------------


Agent-Trex-to-Taste-Dataview DEFINITIONS ::=
BEGIN


-- Import of TASTE predefined basic types (TASTE-ExtendedTypes DEFINITIONS)
IMPORTS T-UInt32, T-Boolean, T-Int32 FROM TASTE-BasicTypes T-Double, T-Float, T-Int64, T-UInt16, T-String FROM TASTE-ExtendedTypes;


-- Basic TREX-AGENT types
IntegerIntervalDomain ::= SEQUENCE{
    min   T-Int64,
    max   T-Int64
}

FloatIntervalDomain ::= SEQUENCE{
    min   T-Float,
    max   T-Float
}

HotdockcmdPred ::= ENUMERATED { hotdockcmd-sendstate, hotdockcmd-idle, hotdockcmd-cancel, hotdockcmd-unknown }
HotdockstatusPred ::= ENUMERATED { hotdockstatus-status, hotdockstatus-cancel, hotdockstatus-unknown }
WmcmdPred ::= ENUMERATED { wmcmd-error, wmcmd-movetohd, wmcmd-movetoslot, wmcmd-idle, wmcmd-cancel, wmcmd-unknown }
WmstatusPred ::= ENUMERATED { wmstatus-status, wmstatus-cancel, wmstatus-unknown }
BasecmdPred ::= ENUMERATED { basecmd-error, basecmd-switchbase, basecmd-baseat, basecmd-cancel, basecmd-unknown }
EfcmdPred ::= ENUMERATED { efcmd-pick, efcmd-drop, efcmd-idle, efcmd-picked, efcmd-error, efcmd-cancel, efcmd-unknown }
SodmissionPred ::= ENUMERATED { sodmission-pick, sodmission-dropsm, sodmission-changebase, sodmission-executefromfile, sodmission-picked, sodmission-idle, sodmission-cancel, sodmission-unknown }
SodplannerPred ::= ENUMERATED { sodplanner-fault, sodplanner-planning, sodplanner-idle, sodplanner-failed, sodplanner-cancel, sodplanner-unknown }
PlannerPred ::= ENUMERATED { planner-fault, planner-idle, planner-planning, planner-cancel, planner-unknown }
MissionPred ::= ENUMERATED { mission-place, mission-loadinge3plan, mission-idle, mission-cancel, mission-unknown }
AutonomyPred ::= ENUMERATED { autonomy-e1, autonomy-e2, autonomy-e3, autonomy-e4, autonomy-cancel, autonomy-unknown }

-- ACTIONSTATUS ENUM DATA (AGENT-FUNCTIONAL)
ActionstatusEnum ::= ENUMERATED { actionstatus-success, actionstatus-failed, actionstatus-notachievable, actionstatus-notenoughtime, actionstatus-unknown }

-- STATEID ENUM DATA (AGENT-FUNCTIONAL)
StateidEnum ::= ENUMERATED { stateid-offline, stateid-idle, stateid-aligned, stateid-latched, stateid-connected, stateid-locked, stateid-unknown }

-- COMMANDSTATE ENUM DATA (AGENT-FUNCTIONAL)
CommandstateEnum ::= ENUMERATED { commandstate-offline, commandstate-idle, commandstate-latched, commandstate-connected, commandstate-unknown }

-- YAWID ENUM DATA (AGENT-FUNCTIONAL)
YawidEnum ::= ENUMERATED { yawid-yaw0, yawid-yaw90, yawid-yaw180, yawid-yaw270, yawid-unknown }
 


-- BOOLD DOMAIN DATA (AGENT-FUNCTIONAL)
Boold ::= SEQUENCE {
    value        T-Int64
    
}

-- INTD DOMAIN DATA (AGENT-FUNCTIONAL)
Intd ::= SEQUENCE {
    value        T-Int64
    
}

-- FLOATD DOMAIN DATA (AGENT-FUNCTIONAL)
Floatd ::= SEQUENCE {
    value        T-Float
    
}

-- STRINGD DOMAIN DATA (AGENT-FUNCTIONAL)
Stringd ::= SEQUENCE {
    value        T-String
    
}

-- INT2D DOMAIN DATA (AGENT-FUNCTIONAL)
Int2d ::= SEQUENCE {
    x        T-Int64,
    y        T-Int64
    
}

-- INT3D DOMAIN DATA (AGENT-FUNCTIONAL)
Int3d ::= SEQUENCE {
    x        T-Int64,
    y        T-Int64,
    z        T-Int64
    
}

-- POSITION3D DOMAIN DATA (AGENT-FUNCTIONAL)
Position3D ::= SEQUENCE {
    x        T-Float,
    y        T-Float
    
}

-- QUATERNIOND DOMAIN DATA (AGENT-FUNCTIONAL)
Quaterniond ::= SEQUENCE {
    x        T-Float,
    y        T-Float
    
}
 


-- HOTDOCKCMD TIMELINE DATA (AGENT-FUNCTIONAL)
Hotdockcmdstatus ::= SEQUENCE {
    predicate       HotdockcmdPred,
    inittime        IntegerIntervalDomain,
    endtime        IntegerIntervalDomain,
    sm        Stringd,
    hotdock        Stringd,
    hdstate        StateidEnum,
    status        ActionstatusEnum
    
}

-- HOTDOCKSTATUS TIMELINE DATA (AGENT-FUNCTIONAL)
Hotdockstatusstatus ::= SEQUENCE {
    predicate       HotdockstatusPred,
    inittime        IntegerIntervalDomain,
    endtime        IntegerIntervalDomain,
    pathfile        Stringd
    
}

-- WMCMD TIMELINE DATA (AGENT-FUNCTIONAL)
Wmcmdstatus ::= SEQUENCE {
    predicate       WmcmdPred,
    inittime        IntegerIntervalDomain,
    endtime        IntegerIntervalDomain,
    hdid        Stringd,
    slot        Int3d,
    face        Stringd,
    yaw        Stringd,
    status        ActionstatusEnum
    
}

-- WMSTATUS TIMELINE DATA (AGENT-FUNCTIONAL)
Wmstatusstatus ::= SEQUENCE {
    predicate       WmstatusPred,
    inittime        IntegerIntervalDomain,
    endtime        IntegerIntervalDomain,
    pathfile        Stringd
    
}

-- BASECMD TIMELINE DATA (AGENT-FUNCTIONAL)
Basecmdstatus ::= SEQUENCE {
    predicate       BasecmdPred,
    inittime        IntegerIntervalDomain,
    endtime        IntegerIntervalDomain,
    hdid        Stringd,
    status        ActionstatusEnum
    
}

-- EFCMD TIMELINE DATA (AGENT-FUNCTIONAL)
Efcmdstatus ::= SEQUENCE {
    predicate       EfcmdPred,
    inittime        IntegerIntervalDomain,
    endtime        IntegerIntervalDomain,
    hdid        Stringd,
    status        ActionstatusEnum
    
}

-- SODMISSION TIMELINE DATA (AGENT-FUNCTIONAL)
Sodmissionstatus ::= SEQUENCE {
    predicate       SodmissionPred,
    inittime        IntegerIntervalDomain,
    endtime        IntegerIntervalDomain,
    face        Stringd,
    sm        Stringd,
    slot        Stringd,
    orientation        Stringd,
    filename        Stringd,
    status        ActionstatusEnum
    
}

-- SODPLANNER TIMELINE DATA (AGENT-FUNCTIONAL)
Sodplannerstatus ::= SEQUENCE {
    predicate       SodplannerPred,
    inittime        IntegerIntervalDomain,
    endtime        IntegerIntervalDomain
    
}

-- PLANNER TIMELINE DATA (AGENT-FUNCTIONAL)
Plannerstatus ::= SEQUENCE {
    predicate       PlannerPred,
    inittime        IntegerIntervalDomain,
    endtime        IntegerIntervalDomain
    
}

-- MISSION TIMELINE DATA (AGENT-FUNCTIONAL)
Missionstatus ::= SEQUENCE {
    predicate       MissionPred,
    inittime        IntegerIntervalDomain,
    endtime        IntegerIntervalDomain,
    sm        Stringd,
    slot        Stringd,
    orientation        Stringd,
    file        Stringd
    
}

-- AUTONOMY TIMELINE DATA (AGENT-FUNCTIONAL)
Autonomystatus ::= SEQUENCE {
    predicate       AutonomyPred,
    inittime        IntegerIntervalDomain,
    endtime        IntegerIntervalDomain
    
}
 


-- ASN.1 Type definitions must start with an uppercase
-- Field names in records (SEQUENCE) must start with a lowercase
-- Underscores are not allowed: use dash (hyphen) 

END

-- H2020 ESROCOS Project
-- Company: GMV Aerospace & Defence S.A.U.
-- Licence: GPLv2

-- ASN.1 definitions for private service ST[200] Timeline Control
--
-- Several subservices are implemented:
--  - TM[200,18] planner report
 
--  - TC[200,19] mission request
--  - TM[200,20] mission report
 
--  - TC[200,13] sodmission request
--  - TM[200,14] sodmission report
 
--  - TC[200,1] hotdockcmd request
--  - TM[200,2] hotdockcmd report

--  - TM[200,4] hotdockstatus report
 
--  - TC[200,5] wmcmd request
--  - TM[200,6] wmcmd report
 
--  - TC[200,9] basecmd request
--  - TM[200,10] basecmd report
 
--  - TC[200,11] efcmd request
--  - TM[200,12] efcmd report

--  - TM[200,8] wmstatus report

--  - TM[200,16] sodplanner report


PUS-ST200 DEFINITIONS ::= 
BEGIN

    IMPORTS 
    PusUInt32 FROM PUS-TypesDefinitions
    T-String FROM TASTE-ExtendedTypes
    Plannerstatus FROM Agent-Trex-to-Taste-Dataview
    Missionstatus FROM Agent-Trex-to-Taste-Dataview
    Sodmissionstatus FROM Agent-Trex-to-Taste-Dataview
    Hotdockcmdstatus FROM Agent-Trex-to-Taste-Dataview
    Hotdockstatusstatus FROM Agent-Trex-to-Taste-Dataview
    Wmcmdstatus FROM Agent-Trex-to-Taste-Dataview
    Basecmdstatus FROM Agent-Trex-to-Taste-Dataview
    Efcmdstatus FROM Agent-Trex-to-Taste-Dataview
    Wmstatusstatus FROM Agent-Trex-to-Taste-Dataview
    Sodplannerstatus FROM Agent-Trex-to-Taste-Dataview
    ;
    
    -- Data for TM[200,18]
    PusTM-200-18-Data ::= SEQUENCE
    {
    	observation Plannerstatus,
        agent T-String
    }
    
     
    -- Data for TC[200,19]
    PusTC-200-19-Data ::= SEQUENCE
    {
    	goal Missionstatus,
        agent T-String
    }
    
    -- Data for TM[200,20]
    PusTM-200-20-Data ::= SEQUENCE
    {
    	observation Missionstatus,
        agent T-String
    }
    
     
    -- Data for TC[200,13]
    PusTC-200-13-Data ::= SEQUENCE
    {
    	goal Sodmissionstatus,
        agent T-String
    }
    
    -- Data for TM[200,14]
    PusTM-200-14-Data ::= SEQUENCE
    {
    	observation Sodmissionstatus,
        agent T-String
    }
    
     
    -- Data for TC[200,1]
    PusTC-200-1-Data ::= SEQUENCE
    {
    	goal Hotdockcmdstatus,
        agent T-String
    }
    
    -- Data for TM[200,2]
    PusTM-200-2-Data ::= SEQUENCE
    {
    	observation Hotdockcmdstatus,
        agent T-String
    }
    
    
    -- Data for TM[200,4]
    PusTM-200-4-Data ::= SEQUENCE
    {
    	observation Hotdockstatusstatus,
        agent T-String
    }
    
     
    -- Data for TC[200,5]
    PusTC-200-5-Data ::= SEQUENCE
    {
    	goal Wmcmdstatus,
        agent T-String
    }
    
    -- Data for TM[200,6]
    PusTM-200-6-Data ::= SEQUENCE
    {
    	observation Wmcmdstatus,
        agent T-String
    }
    
     
    -- Data for TC[200,9]
    PusTC-200-9-Data ::= SEQUENCE
    {
    	goal Basecmdstatus,
        agent T-String
    }
    
    -- Data for TM[200,10]
    PusTM-200-10-Data ::= SEQUENCE
    {
    	observation Basecmdstatus,
        agent T-String
    }
    
     
    -- Data for TC[200,11]
    PusTC-200-11-Data ::= SEQUENCE
    {
    	goal Efcmdstatus,
        agent T-String
    }
    
    -- Data for TM[200,12]
    PusTM-200-12-Data ::= SEQUENCE
    {
    	observation Efcmdstatus,
        agent T-String
    }
    
    
    -- Data for TM[200,8]
    PusTM-200-8-Data ::= SEQUENCE
    {
    	observation Wmstatusstatus,
        agent T-String
    }
    
    
    -- Data for TM[200,16]
    PusTM-200-16-Data ::= SEQUENCE
    {
    	observation Sodplannerstatus,
        agent T-String
    }
    

END

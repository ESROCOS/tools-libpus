-- H2020 ESROCOS Project
-- Company: GMV Aerospace & Defence S.A.U.
-- Licence: GPLv2

-- ASN.1 definitions for service ST[210] RMAP management
--
-- Limitations:
-- * This is part of a prototype for a demonstration


PUS-ST210 DEFINITIONS ::=
BEGIN

    IMPORTS
    PusUInt16, PusUInt8, PusInt32, PusBoolean, PusFloat32, PusDouble FROM PUS-TypesDefinitions
--    PusSt03ParameterId, PusSt03HousekeepingReportId FROM PUS-ST03
    ;
  
/* R_ICU_SPW_PNP */
    -- Data for TC[210,1]
    PusTC-210-1-Data ::= SEQUENCE
    {
        smId PusUInt8,
        componentId PusUInt8,
        routingTableIndex PusUInt8,
        routingTableDirection PusUInt8,
        trafficPriority PusUInt8
    }
    -- Data for TC[210,2]
    PusTC-210-2-Data ::= SEQUENCE
    {
        smId PusUInt8,
        componentId PusUInt8,
        setOwner PusUInt8
    }
/* R_ICU */
    -- Data for TC[210,11]
    PusTC-210-11-Data ::= SEQUENCE
    {
        smId PusUInt8,
        componentId PusUInt8,
        secsSinceEpoch PusInt32,
        nanosecsSinceEpoch PusInt32
    }
    -- Data for TC[210,12]
    PusTC-210-12-Data ::= SEQUENCE
    {
        smId PusUInt8,
        componentId PusUInt8,
        setLeds PusUInt8
    }
/* HOTDOCK */
    -- Data for TC[210,21]
    PusTC-210-21-Data ::= SEQUENCE
    {
        smId PusUInt8,
        componentId PusUInt8,
        subcomponentId PusUInt8,
        pollingHkTm PusUInt8
    }
    -- Data for TC[210,22]
    PusTC-210-22-Data ::= SEQUENCE
    {
        smId PusUInt8,
        componentId PusUInt8,
        subcomponentId PusUInt8,
        targetState PusUInt8
    }
    -- Data for TC[210,23]
    PusTC-210-23-Data ::= SEQUENCE
    {
        smId PusUInt8,
        componentId PusUInt8,
        subcomponentId PusUInt8,
        p15vCmd PusBoolean
    }
    -- Data for TC[210,24]
    PusTC-210-24-Data ::= SEQUENCE
    {
        smId PusUInt8,
        componentId PusUInt8,
        subcomponentId PusUInt8,
        p2v5Cmd PusBoolean
    }
    -- Data for TC[210,25]
    PusTC-210-25-Data ::= SEQUENCE
    {
        smId PusUInt8,
        componentId PusUInt8,
        subcomponentId PusUInt8,
        relayCmd PusBoolean
    }
    -- Data for TC[210,26]
    PusTC-210-26-Data ::= SEQUENCE
    {
        smId PusUInt8,
        componentId PusUInt8,
        subcomponentId PusUInt8,
        lvdsACmd PusUInt8,
        lvdsBCmd PusUInt8
    }
    -- Data for TC[210,27]
    PusTC-210-27-Data ::= SEQUENCE
    {
        smId PusUInt8,
        componentId PusUInt8,
        subcomponentId PusUInt8,
        motorOnOff PusBoolean
    }
    -- Data for TC[210,28]
    PusTC-210-28-Data ::= SEQUENCE
    {
        smId PusUInt8,
        componentId PusUInt8,
        subcomponentId PusUInt8,
        motorTargetSpeed PusFloat32
    }
    -- Data for TC[210,29]
    PusTC-210-29-Data ::= SEQUENCE
    {
        smId PusUInt8,
        componentId PusUInt8,
        subcomponentId PusUInt8,
        motorDirectionSpeed PusBoolean
    }
    -- Data for TC[210,30]
    PusTC-210-30-Data ::= SEQUENCE
    {
        smId PusUInt8,
        componentId PusUInt8,
        subcomponentId PusUInt8,
        motorCurrentLimit PusFloat32
    }
    -- Data for TC[210,31]
    PusTC-210-31-Data ::= SEQUENCE
    {
        smId PusUInt8,
        componentId PusUInt8,
        subcomponentId PusUInt8,
        controllerCalib PusUInt8
    }
    -- Data for TC[210,32]
    PusTC-210-32-Data ::= SEQUENCE
    {
        smId PusUInt8,
        componentId PusUInt8,
        subcomponentId PusUInt8
    }
/* OSP */
    -- Data for TC[210,41]
    PusTC-210-41-Data ::= SEQUENCE
    {
        smId PusUInt8,
        componentId PusUInt8,
        command PusUInt8
    }
    -- Data for TC[210,42]
    PusTC-210-42-Data ::= SEQUENCE
    {
        smId PusUInt8,
        componentId PusUInt8
    }
/* BAT */
    -- Data for TC[210,61]
    PusTC-210-61-Data ::= SEQUENCE
    {
        smId PusUInt8,
        componentId PusUInt8
    }
    -- Data for TC[210,62]
    PusTC-210-62-Data ::= SEQUENCE
    {
        smId PusUInt8,
        componentId PusUInt8
    }
    -- Data for TC[210,63]
    PusTC-210-63-Data ::= SEQUENCE
    {
        smId PusUInt8,
        componentId PusUInt8
    }
    -- Data for TC[210,64]
    PusTC-210-64-Data ::= SEQUENCE
    {
        smId PusUInt8,
        componentId PusUInt8,
        targetState PusUInt8
    }
    -- Data for TC[210,65]
    PusTC-210-65-Data ::= SEQUENCE
    {
        smId PusUInt8,
        componentId PusUInt8,
        conv48vCmd PusBoolean
    }
    -- Data for TC[210,66]
    PusTC-210-66-Data ::= SEQUENCE
    {
        smId PusUInt8,
        componentId PusUInt8,
        batChCmd PusBoolean
    }
/* WM */
    -- Data for TC[210,71]
    PusTC-210-71-Data ::= SEQUENCE
    {
        smId PusUInt8,
        componentId PusUInt8,
        nSteps PusUInt8,
        -- matrix [50][7]
        goalValues SEQUENCE SIZE(350) OF PusDouble
    }
    -- Data for TC[210,72]
    PusTC-210-72-Data ::= SEQUENCE
    {
        smId PusUInt8,
        componentId PusUInt8,
        -- matrix [3][4]
        desiredPos SEQUENCE SIZE(12) OF PusDouble
    }
    -- Data for TC[210,73]
    PusTC-210-73-Data ::= SEQUENCE
    {
        smId PusUInt8,
        componentId PusUInt8,
        setMode PusInt32,
        hdId PusInt32,
        manipulatorBase PusInt32,
        graspRelease PusInt32
    }
/* THS */
    -- Data for TC[210,81]
    PusTC-210-81-Data ::= SEQUENCE
    {
        smId PusUInt8,
        componentId PusUInt8,
        targetMode PusUInt8
    }
    -- Data for TC[210,82]
    PusTC-210-82-Data ::= SEQUENCE
    {
        smId PusUInt8,
        componentId PusUInt8,
        componentTargetId PusUInt8,
        componentTargetStatus PusBoolean
    }
/* CPDU */
    -- Data for TC[210,91]
    PusTC-210-91-Data ::= SEQUENCE
    {
        smId PusUInt8,
        componentId PusUInt8,
        subcomponentId PusUInt8,
        hkXRequest PusUInt8
    }
    -- Data for TC[210,92]
    PusTC-210-92-Data ::= SEQUENCE
    {
        smId PusUInt8,
        componentId PusUInt8,
        subcomponentId PusUInt8
    }
    -- Data for TC[210,93]
    PusTC-210-93-Data ::= SEQUENCE
    {
        smId PusUInt8,
        componentId PusUInt8,
        subcomponentId PusUInt8,
        sw1Cmd PusBoolean,
        sw2Cmd PusBoolean,
        sw3Cmd PusBoolean,
        sw4Cmd PusBoolean,
        sw5Cmd PusBoolean
    }
    -- Data for TC[210,94]
    PusTC-210-94-Data ::= SEQUENCE
    {
        smId PusUInt8,
        componentId PusUInt8,
        subcomponentId PusUInt8,
        conv24vACmd PusBoolean,
        conv24vBCmd PusBoolean,
        conv12vCmd PusBoolean,
        conv19vCmd PusBoolean
    }
    -- Data for TC[210,95]
    PusTC-210-95-Data ::= SEQUENCE
    {
        smId PusUInt8,
        componentId PusUInt8,
        subcomponentId PusUInt8
    }
    
END

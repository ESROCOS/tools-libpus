-- H2020 ESROCOS Project
-- Company: GMV Aerospace & Defence S.A.U.
-- Licence: GPLv2

-- ASN.1 definitions for private service ST[20] Control camera
--
-- Two subservices are implemented:
--  - TC[200,1] Control camera request
--  - TM[200,2] Control camera report


PUS-ST200 DEFINITIONS ::= 
BEGIN


    IMPORTS 
    PusUInt32 FROM PUS-TypesDefinitions
    ;
    
    -- Control camera operation ID
    PusSt200ControlId ::= PusUInt32
    
    -- Control camera observation
    PusSt200Observation ::= PusUInt32

    
    -- Data for TC[200,1]
    PusTC-200-1-Data  ::= SEQUENCE
    {
    	controlId PusSt200ControlId
    }
    
    -- Data for TM[200,1]
    PusTM-200-2-Data  ::= SEQUENCE
    {
    	observation PusSt200Observation
    }
    
END
